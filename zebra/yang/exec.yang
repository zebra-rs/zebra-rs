module exec {
  yang-version "1";

  namespace "urn:ietf:params:xml:ns:yang:zebra";
  prefix "exec";

  import ietf-inet-types {
    prefix inet;
  }

  import extension {
    prefix ext;
  }

  leaf help {
    ext:help "Show help";
    type empty;
  }

  leaf configure {
    ext:help "Manipulate software configuration information";
    type empty;
  }

  container show {
    ext:help "Show command";
    leaf version {
      ext:help "Show version";
      type empty;
    }
    leaf nexthop {
      ext:help "Show nexthop group";
      type empty;
    }
    leaf community-list {
      ext:help "Show community-list";
      type empty;
    }
    list interface {
      ext:help "Show interface commands";
      key "if-name";
      leaf if-name {
        type string;
      }
      leaf detail {
        type string;
      }
    }
    leaf hostname {
      type string;
      description
        "The name of the host.  This name can be a single domain
        label or the fully qualified domain name of the host.";
    }
    container ip {
      ext:help "Show IP commands";
      leaf route {
        ext:help "IP route prefix";
        // type inet:ipv4-prefix;
        type empty;
      }
      container bgp {
        ext:help "BGP commands";
        presence "BGP RIB";
        leaf summary {
          ext:help "BGP summary information";
          type empty;
        }
        container neighbor {
          ext:help "BGP neighbor information";
          presence "all neighbor";
          leaf address {
            type string;
          }
        }
      }

      container ospf {
        ext:help "OSPF commands";
        presence "OSPF instance";
        leaf interface {
          ext:help "OSPF interface";
          type empty;
        }
        leaf neighbor {
          ext:help "OSPF neighbor";
          type empty;
        }
        leaf database {
          ext:help "OSPF database";
          type empty;
        }
      }
    }

    container isis {
      ext:help "IS-IS commands";
      presence "IS-IS instance";
      leaf summary {
        ext:help "IS-IS summary";
        type empty;
      }
      container interface {
        ext:help "IS-IS interface";
        presence "IS-IS interface";
        leaf detail {
          ext:help "IS-IS interface detail";
          type empty;
        }
      }
      container adjacency {
        ext:help "IS-IS adjacency";
        presence "IS-IS adjacency";
        leaf detail {
          ext:help "IS-IS adjacency detail";
          type empty;
        }
      }
      container neighbor {
        ext:help "IS-IS neighbor";
        presence "IS-IS neighbor";
        leaf detail {
          ext:help "IS-IS neighbor detail";
          type empty;
        }
      }
      leaf hostname {
        ext:help "IS-IS hostname";
        type empty;
      }
      container database {
        ext:help "IS-IS database";
        presence "IS-IS database";
        leaf detail {
          ext:help "IS-IS database detail";
          type empty;
        }
      }
    }
    container ipv6 {
      ext:help "Show IPv6 commands";
      leaf route {
        ext:help "IPv6 address";
        type inet:ipv6-address;
      }
      leaf prefix {
        ext:help "IPv6 prefix";
        type inet:ipv6-prefix;
      }
    }
  }
  container cli {
    ext:help "Command line interface";
    leaf format {
      ext:help "CLI output format";
      type enumeration {
        enum terminal {
          description "Terminal output format";
        }
        enum json {
          description "JSON output";
        }
      }
    }
  }
}

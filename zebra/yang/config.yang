module config {
  yang-version "1";

  namespace "urn:ietf:params:xml:ns:yang:zebra";
  prefix "config";

  import ietf-inet-types {
    prefix inet;
  }

  import ietf-yang-types {
    prefix yang;
  }

  import extension {
    prefix ext;
  }

  import dhcp {
    prefix dhcp;
  }

  import ietf-bgp {
    prefix bgp;
  }

  import ietf-bgp-policy {
    prefix policy;
  }

  import openconfig-isis-types {
    prefix isis;
  }

  grouping config {
    container system {
      ext:help "System configuration";
      description
        "System group configuration.";

      leaf hostname {
        type string;
        description
          "The name of the host. This name can be a single domain label or the
           fully qualified domain name of the host.";
      }
      leaf empty {
        type empty;
      }
      leaf-list track-interface {
        type string;
        description
          "Interfaces to track.";
      }
      container presence {
        presence "Presence container";
      }
      container dhcp {
        uses "dhcp:dhcp";
      }
      container etcd {
        list endpoints {
          key "url";
          leaf url {
            type string;
          }
        }
        leaf path {
          type string;
        }
      }
    }

    container routing {
      ext:help "Routing configuration";
      uses "ietf-bgp:bgp";
      // uses "policy:defined-sets";
      container ospf {
        presence "Enables configuration of OSPFv2";
        leaf router-id {
          type inet:ipv4-address;
        }
        list network {
          key prefix;
          leaf prefix {
            type inet:ipv4-prefix;
          }
          leaf area {
            mandatory true;
            type uint8;
          }
        }
      }
      container isis {
        presence "Enables configuration of IS-IS";

        leaf net {
          type isis:net;
        }
      }
      container ldp {
        leaf router-id {
          type inet:ipv4-address;
        }
        leaf target-address {
          type inet:ipv4-address;
        }
        list interface {
          key "name";
          leaf name {
            type string;
          }
          leaf enable {
            type empty;
          }
        }
      }
      container static {
        ext:help "Static route configuration";
        container ipv4 {
          ext:help "IPv4 configuration";
          list route {
            key "prefix";
            leaf prefix {
              type inet:ipv4-prefix;
            }
            list nexthop {
              key "address";
              leaf "address" {
                type inet:ipv4-address;
                description "Nexthop of the route";
              }
              leaf metric {
                type uint32;
                description "Metric of the route.";
              }
              leaf weight {
                type uint8;
                description "Weight of ECMP route.";
              }
            }
            leaf distance {
              type uint8;
              description "Distance of the route.";
            }
            leaf metric {
              type uint32;
              description "Metric of the route.";
            }
          }

          list arp {
            key "address";
            leaf "address" {
              type inet:ipv4-address;
              description "ARP neighbor address";
            }
            leaf mac {
              type yang:mac-address;
              description "MAC Address";
            }
          }

          list srv6 {
            key "prefix";
            leaf prefix {
              type inet:ipv4-prefix;
            }
            leaf encap {
              type enumeration {
                enum seg6;
                enum seg6local;
              }
            }
            leaf mode {
              type enumeration {
                enum encap;
                enum inline;
              }
            }
            leaf-list segs {
              type string;
              description "SRv6 segments";
            }
            leaf action {
              type enumeration {
                enum End;
                enum End.DT4;
              }
            }
            leaf dev {
              type string;
              description "Outgoing interface";
            }
            leaf table {
              type uint32;
            }
            leaf flavors {
              type enumeration {
                enum next-csid;
                enum psp;
                enum usp;
                enum usd;
              }
            }
            leaf lblen {
              type uint8;
            }
            leaf nflen {
              type uint8;
            }
          }

          list lsp {
            key "prefix";
            leaf prefix {
              type inet:ipv4-prefix;
            }
            leaf-list encap {
              type uint32;
            }
            leaf "nexthop" {
              type inet:ipv4-address;
              description "Nexthop of the route";
            }
            leaf metric {
              type uint32;
              description "Metric of the route.";
            }
          }
        }
        container ipv6 {
          ext:help "IPv6 configuration";

          list neighbor {
            key "address";
            leaf "address" {
              type inet:ipv6-address;
              description "ARP neighbor address";
            }
            leaf mac {
              type yang:mac-address;
              description "MAC Address";
            }
          }

          list route {
            key "prefix";
            leaf prefix {
              type inet:ipv6-prefix;
            }
            list nexthop {
              key "address";
              leaf "address" {
                type inet:ipv6-address;
                description "Nexthop of the route";
              }
              leaf metric {
                type uint32;
                description "Metric of the route.";
              }
              leaf weight {
                type uint8;
                description "Weight of ECMP route.";
              }
            }
            leaf distance {
              type uint8;
              description "Distance of the route.";
            }
            leaf metric {
              type uint32;
              description "Metric of the route.";
            }
          }
        }

      }
    }

    list community-list {
      description
        "Enclosing container for list of defined BGP community
           sets.";
      key "name";
      description
        "List of defined BGP community sets.";
      leaf name {
        type string;
        description
          "Name / label of the community set -- this is used to
               reference the set in match conditions.";
      }
      list seq {
        key "seq";
        description
          "List of defined BGP community sets.";
        leaf seq {
          type uint32;
          description
            "Name / label of the community set -- this is used to
               reference the set in match conditions.";
        }
        leaf action {
          mandatory true;
          type enumeration {
            enum permit;
            enum deny;
          }
        }
        leaf-list member {
          type string;
          description
            "Members of the community set";
        }
      }
    }
    list prefix-list {
      description
        "Enclosing container for list of defined BGP community
           sets.";
      key "name";
      description
        "List of defined BGP community sets.";
      leaf name {
        type string;
        description
          "Name / label of the community set -- this is used to
               reference the set in match conditions.";
      }
      list seq {
        key "seq";
        description
          "List of defined BGP community sets.";
        leaf seq {
          type uint32;
          description
            "Name / label of the community set -- this is used to
               reference the set in match conditions.";
        }
        leaf action {
          mandatory true;
          type enumeration {
            enum permit;
            enum deny;
          }
        }
        leaf prefix {
          type inet:ipv4-prefix;
          description
            "Members of the community set";
        }
        leaf le {
          type uint8;
          description
            "Members of the community set";
        }
        leaf eq {
          type uint8;
          description
            "Members of the community set";
        }
        leaf ge {
          type uint8;
          description
            "Members of the community set";
        }
      }
    }
    container interfaces {
      list interface {
        key "name";
        leaf name {
          type string;
        }
      }
    }
    list vrf {
      key "name";
      leaf name {
        type string;
      }
      leaf id {
        mandatory true;
        type uint32;
      }
    }
  }
}

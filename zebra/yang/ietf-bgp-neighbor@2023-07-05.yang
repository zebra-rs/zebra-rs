submodule ietf-bgp-neighbor {
  yang-version 1.1;
  belongs-to ietf-bgp {
    prefix bgp;
  }

  import ietf-yang-types {
    prefix yang;
    reference
      "RFC 6991: Common YANG Data Types.";
  }

  import iana-bgp-types {
    prefix bt;
    reference
      "RFC XXXX: YANG Model for Border Gateway Protocol (BGP-4).";
  }

  // Include the common submodule

  include ietf-bgp-common;
  include ietf-bgp-common-multiprotocol;
  include ietf-bgp-common-structure;

  // meta

  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jhaas at juniper.net).";

  description
    "This sub-module contains groupings that are specific to the
     neighbor context of the BGP module.

     Copyright (c) 2023 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2023-07-05 {
    description
      "Initial Version";
    reference
      "RFC XXXX: YANG Model for Border Gateway Protocol (BGP-4).";
  }

  grouping bgp-neighbor-afi-safi-list {
    description
      "List of address-families associated with the BGP neighbor";
    list afi-safi {
      key "name";
      description
        "AFI, SAFI configuration available for the neighbor or
         group";
      uses mp-afi-safi-config;
      // leaf active {
      //   type boolean;
      //   config false;
      //   description
      //     "This value indicates whether a particular AFI-SAFI has
      //      been successfully negotiated with the peer. An AFI-SAFI
      //      may be enabled in the current running configuration, but
      //      a session restart may be required in order to negotiate
      //      the new capability.";
      // }
      container prefixes {
        config false;
        description
          "Prefix counters for the AFI/SAFI in this BGP session";
        leaf received {
          type yang:zero-based-counter32;
          description
            "The number of prefixes received from the neighbor";
        }
        leaf sent {
          type yang:zero-based-counter32;
          description
            "The number of prefixes advertised to the neighbor";
        }
        leaf installed {
          type yang:gauge32;
          description
            "The number of advertised prefixes installed in the
             Loc-RIB";
        }
      }
      container graceful-restart {
        if-feature "bt:graceful-restart";
        description
          "Parameters relating to BGP graceful-restart";
        reference
          "RFC 4724: Graceful Restart Mechanism for BGP.";
        uses mp-afi-safi-graceful-restart-config;
        leaf received {
          type boolean;
          config false;
          description
            "This leaf indicates whether the neighbor advertised the
             ability to support graceful-restart for this AFI-SAFI";
          reference
            "RFC 4724: Graceful Restart Mechanism for BGP, Section
             3.";
        }
        leaf advertised {
          type boolean;
          config false;
          description
            "This leaf indicates whether the ability to support
             graceful-restart has been advertised to the peer";
          reference
            "RFC 4724: Graceful Restart Mechanism for BGP, Section
             3.";
        }
        leaf local-forwarding-state-preserved {
          type boolean;
          config false;
          description
            "This leaf indicates whether the local router has
             or would advertise the Forwarding State bit in its
             Graceful Restart capability for this AFI-SAFI.";
          reference
            "RFC 4724: Graceful Restart Mechanism for BGP, Section
             3.";
        }
        leaf forwarding-state-preserved {
          type boolean;
          config false;
          description
            "This leaf indicates whether the neighbor has advertised
             the Forwarding State bit in its Graceful Restart
             capability for this AFI-SAFI.";
          reference
            "RFC 4724: Graceful Restart Mechanism for BGP, Section
             3.";
        }
        leaf end-of-rib-received {
          type boolean;
          config false;
          description
            "This leaf indicates whether the neighbor has advertised
             the End-of-RIB marker for this AFI-SAFI.";
          reference
            "RFC 4724: Graceful Restart Mechanism for BGP, Section
             2.";
        }
      }
      // uses mp-all-afi-safi-list-contents;
      uses bgp-neighbor-use-multiple-paths;
    }
  }
}

module config-static {
  yang-version "1";

  namespace "urn:ietf:params:xml:ns:yang:zebra-static";
  prefix "static";

  import ietf-inet-types {
    prefix inet;
  }

  import ietf-yang-types {
    prefix yang;
  }

  import extension {
    prefix ext;
  }

  description
    "Schema for the zebra-rs static-routing tree. Extracted from
     config.yang so the same shape can be instantiated twice — once
     at the global level (`router static {...}`, the default VRF)
     and once inside each per-VRF entry (`router static vrf NAME
     {...}`). The on-the-wire data tree is unchanged for the global
     instantiation; the per-VRF tree mirrors it under each VRF key.";

  grouping static-routes {
    description
      "Address-family static-routing constructs (mpls + ipv4 + ipv6).
       `uses` this grouping wherever a routing-instance-scoped static
       configuration is needed.";

    container mpls {
      ext:help "MPLS label configuration";
      list label {
        ext:help "MPLS label entry";
        key "value";
        leaf value {
          ext:help "Incoming label value";
          type uint32;
        }
        list nexthop {
          ext:help "Label nexthop";
          key "address";
          leaf "address" {
            ext:help "Nexthop address, or blackhole to discard";
            type union {
              type inet:ipv4-address;
              // An IPv6 nexthop makes this a static ILM over a
              // v6-numbered core (RTA_VIA inet6 in the kernel, a v6
              // adjacency in the eBPF tee) — the transit shape of
              // MPLS-over-v6 PEs.
              type inet:ipv6-address;
              // `blackhole` at the nexthop-key position turns the
              // route into a discard route (kernel RTN_BLACKHOLE),
              // satisfying the route's `ext:non-empty "nexthop"`.
              type enumeration {
                enum blackhole;
              }
            }
            description "Nexthop address, or `blackhole` to discard";
          }
          leaf "outgoing-label" {
            ext:help "Outgoing MPLS label";
            type uint32;
          }
          leaf interface {
            ext:help "Egress interface (opts into the eBPF XDP fast-path pop)";
            type string;
            description
              "Explicit egress interface for this label nexthop. Naming
               it opts the pop onto the eBPF XDP fast path, whose
               redirect delivers only toward XDP-attached ports — the
               operator's assertion that this is a core-facing transit
               hop (e.g. a pure-P router popping toward the egress PE,
               which holds no route to the frame's inner destination).
               Left unset, the pop stays on the FIB-assisted path, which
               reaches any device but requires a route for the exposed
               payload.";
          }
        }
      }
    }

    container ipv4 {
      ext:help "IPv4 configuration";
      list route {
        ext:help "IPv4 static route";
        // A bare `route <prefix>` carries no forwarding information — it
        // needs at least a nexthop (or SRv6 / distance / metric child).
        // Reject the key-only entry at commit, and prune it when its last
        // child is deleted, so a meaningless route can't linger.
        ext:non-empty "nexthop";
        key "prefix";
        leaf prefix {
          ext:help "IPv4 destination prefix";
          type inet:ipv4-prefix;
        }
        list nexthop {
          ext:help "Route nexthop";
          key "address";
          leaf "address" {
            ext:help "Nexthop address, or blackhole / unreachable to discard";
            type union {
              type inet:ipv4-address;
              // `blackhole` or `unreachable` at the nexthop-key
              // position turns the route into a discard route,
              // satisfying the route's `ext:non-empty "nexthop"`.
              // `blackhole` drops without a word (kernel
              // RTN_BLACKHOLE); `unreachable` drops and answers the
              // sender with an ICMP Destination Unreachable (kernel
              // RTN_UNREACHABLE). One route takes one of the two.
              type enumeration {
                enum blackhole;
                enum unreachable;
              }
            }
            description
              "Nexthop address, `blackhole` to discard, or `unreachable`
               to discard and tell the sender";
          }
          leaf metric {
            ext:help "Nexthop metric";
            type uint32;
            description "Metric of the route.";
          }
          leaf weight {
            ext:help "ECMP nexthop weight";
            type uint8;
            description "Weight of ECMP route.";
          }
          leaf-list label {
            ext:help "MPLS labels to push";
            type uint32;
          }
        }
        leaf distance {
          ext:help "Administrative distance";
          type uint8;
          description "Distance of the route.";
        }
        leaf blackhole {
          ext:help "Discard route, drop matching traffic";
          type boolean;
          description
            "Discard route: matching traffic is dropped in the
             forwarding plane (kernel RTN_BLACKHOLE) with no
             nexthop. Mutually exclusive with `nexthop`.";
        }
        leaf metric {
          ext:help "Route metric";
          type uint32;
          description "Metric of the route.";
        }
        container srv6 {
          ext:help "SRv6 encapsulation";
          leaf-list segments {
            ext:help "SRv6 segment list";
            type inet:ipv6-address;
          }
          leaf if-name {
            ext:help "Outgoing interface";
            ext:dynamic "rib:interface";
            type string;
          }
        }
      }

      list arp {
        ext:help "Static ARP entry";
        key "address";
        leaf "address" {
          ext:help "ARP neighbor address";
          type inet:ipv4-address;
          description "ARP neighbor address";
        }
        leaf mac {
          ext:help "MAC address";
          type yang:mac-address;
          description "MAC Address";
        }
      }

      list srv6 {
        ext:help "SRv6 route entry";
        key "prefix";
        leaf prefix {
          ext:help "IPv4 destination prefix";
          type inet:ipv4-prefix;
        }
        leaf encap {
          ext:help "SRv6 encapsulation type";
          type enumeration {
            enum seg6;
            enum seg6local;
          }
        }
        leaf mode {
          ext:help "seg6 mode: encap or inline";
          type enumeration {
            enum encap;
            enum inline;
          }
        }
        leaf-list segs {
          ext:help "SRv6 segment list";
          type string;
          description "SRv6 segments";
        }
        leaf action {
          ext:help "seg6local endpoint action";
          type enumeration {
            enum End;
            enum End.DT4;
          }
        }
        leaf dev {
          ext:help "Outgoing interface";
          type string;
          description "Outgoing interface";
        }
        leaf table {
          ext:help "Routing table ID";
          type uint32;
        }
        leaf flavors {
          ext:help "SRv6 endpoint flavor";
          type enumeration {
            enum next-csid;
            enum psp;
            enum usp;
            enum usd;
          }
        }
        leaf lblen {
          ext:help "Locator block length";
          type uint8;
        }
        leaf nflen {
          ext:help "Node function length";
          type uint8;
        }
      }
    }

    container ipv6 {
      ext:help "IPv6 configuration";

      list neighbor {
        ext:help "Static IPv6 neighbor";
        key "address";
        leaf "address" {
          ext:help "IPv6 neighbor address";
          type inet:ipv6-address;
          description "ARP neighbor address";
        }
        leaf mac {
          ext:help "MAC address";
          type yang:mac-address;
          description "MAC Address";
        }
      }

      list route {
        ext:help "IPv6 static route";
        // Sibling of the IPv4 route list: a bare `route <prefix>` is dead
        // config (no nexthop / SRv6 / metric), so reject the key-only entry
        // at commit and prune it on last-child delete.
        ext:non-empty "nexthop";
        key "prefix";
        leaf prefix {
          ext:help "IPv6 destination prefix";
          type inet:ipv6-prefix;
        }
        list nexthop {
          ext:help "Route nexthop";
          key "address";
          leaf "address" {
            ext:help "Nexthop address, or blackhole / unreachable to discard";
            type union {
              type inet:ipv6-address;
              // As for IPv4: `unreachable` answers the sender with an
              // ICMPv6 Destination Unreachable, "no route".
              type enumeration {
                enum blackhole;
                enum unreachable;
              }
            }
            description
              "Nexthop address, `blackhole` to discard, or `unreachable`
               to discard and tell the sender";
          }
          leaf metric {
            ext:help "Nexthop metric";
            type uint32;
            description "Metric of the route.";
          }
          leaf weight {
            ext:help "ECMP nexthop weight";
            type uint8;
            description "Weight of ECMP route.";
          }
          leaf-list label {
            ext:help "MPLS labels to push";
            type uint32;
            description
              "MPLS label stack imposed toward this nexthop, outermost
               first — the IPv6 sibling of the IPv4 nexthop's `label`
               list. This is what gives a labeled transport route to an
               IPv6 PE loopback (SR-MPLS-style over a v6-numbered core)
               without an IGP: EVPN-over-MPLS resolves its transport
               stack from the FIB entry this route installs.";
          }
        }
        leaf distance {
          ext:help "Administrative distance";
          type uint8;
          description "Distance of the route.";
        }
        leaf blackhole {
          ext:help "Discard route, drop matching traffic";
          type boolean;
          description
            "Discard route: matching traffic is dropped in the
             forwarding plane (kernel RTN_BLACKHOLE) with no
             nexthop. Mutually exclusive with `nexthop`.";
        }
        leaf metric {
          ext:help "Route metric";
          type uint32;
          description "Metric of the route.";
        }
        leaf-list segments {
          ext:help "SRv6 segment list";
          type inet:ipv6-address;
        }
        leaf encap-type {
          ext:help "SRv6 encapsulation type";
          type enumeration {
            enum "H.Encap";
            enum "H.Encap.Red";
          }
        }
        leaf action {
          ext:help "SRv6 seg6local endpoint behavior";
          description
            "SRv6 endpoint behavior installed as a seg6local
             terminal action on this prefix. Mutually exclusive
             with `segments` (which configures an outer H.Encap
             push). Usable variants: End, uN, End.DT4, End.DT6,
             End.DT46, and — with the sibling `nh6`/`nh4`
             adjacency leaves — End.DX6 / End.DX4. End.X / uA
             also take `nh6`.

             End.DT4 / End.DT6 / End.DT46 decapsulate the outer
             IPv6 header and look the inner packet up in the VRF
             named by the sibling `vrf` leaf — End.DT4 for the
             VRF's IPv4 unicast table, End.DT6 for IPv6 unicast,
             End.DT46 for both (selected by the inner header's
             address family).";
          type enumeration {
            enum "End";
            enum "End.X";
            enum "uN";
            enum "uA";
            enum "End.DT4";
            enum "End.DT6";
            enum "End.DT46";
            enum "End.DX4";
            enum "End.DX6";
          }
        }
        leaf nh6 {
          ext:help "IPv6 cross-connect nexthop (End.DX6)";
          type inet:ipv6-address;
          description
            "IPv6 cross-connect adjacency for `action End.DX6`
             (decap + forward straight to this neighbor, RFC 8986
             4.4) — also honored for End.X / uA. Mirrors
             iproute2's `nh6` keyword.";
        }
        leaf nh4 {
          ext:help "IPv4 cross-connect nexthop (End.DX4)";
          type inet:ipv4-address;
          description
            "IPv4 cross-connect adjacency for `action End.DX4`
             (RFC 8986 4.5). Mirrors iproute2's `nh4` keyword.";
        }
        leaf vrf {
          ext:help "VRF for End.DT decapsulation lookup";
          type string;
          description
            "Name of the VRF whose routing table is consulted
             after decapsulation. Required when `action` is
             End.DT4, End.DT6, or End.DT46; ignored otherwise.

             Held as a plain string (not a leafref to the
             top-level /vrf list) for the same staging-friendly
             reason as IS-IS uses for `block` and `locator`
             references — a static SID block can be parsed
             before the VRF is declared at the top level.";
        }
      }
    }
  }
}

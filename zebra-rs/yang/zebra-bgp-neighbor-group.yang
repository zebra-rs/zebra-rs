module zebra-bgp-neighbor-group {
  yang-version "1";

  namespace "urn:ietf:params:xml:ns:yang:zebra-bgp-neighbor-group";
  prefix "zbng";

  import ietf-inet-types {
    prefix inet;
  }

  import ietf-bgp {
    prefix bgp;
  }

  import zebra-afi-safi {
    prefix zas;
  }

  import zebra-bgp-transport {
    prefix zbt;
  }

  import zebra-bgp-password {
    prefix zbp;
  }

  import zebra-bgp-allowas-in {
    prefix zbai;
  }

  import zebra-bgp-afi-knobs {
    prefix zbak;
  }

  import zebra-bgp-as-override {
    prefix zbao;
  }

  import zebra-bgp-remove-private-as {
    prefix zbrpa;
  }

  import zebra-bgp-auth {
    prefix zbauth;
  }

  import zebra-bgp-enforce-first-as {
    prefix zbef;
  }

  import zebra-bgp-otc {
    prefix zbotc;
  }

  import zebra-bgp-route-server {
    prefix zbrs;
  }

  import config {
    prefix config;
  }

  import configure {
    prefix configure;
  }

  import extension {
    prefix ext;
  }

  organization
    "zebra-rs";

  contact
    "https://github.com/zebra-rs";

  description
    "IOS-XR-style `neighbor-group` for zebra-rs BGP. The sole
     peer-grouping mechanism (the unimplemented IETF
     `peer-groups/peer-group` container was removed), with a
     deliberately focused attribute surface — the goal is to make the
     common 'these N peers share these few attributes' case ergonomic,
     not to mirror every leaf of `neighbor-group-config`.

     The surface exposes `remote-as` and per-family `afi-safi
     <name> enabled` toggles. Field-level override semantics: any
     field set explicitly on the neighbor wins; otherwise the
     neighbor inherits from the referenced group.

     Resulting CLI / config shape:

       router bgp {
         neighbor-group RR-CLIENTS {
           remote-as 65000;
           afi-safi ipv4 {
             enabled true;
           }
           afi-safi ipv6 {
             enabled true;
           }
         }
         neighbor 10.0.0.1 {
           neighbor-group RR-CLIENTS;
         }
         interface-neighbor eth0 {
           neighbor-group RR-CLIENTS;
         }
       }

     The reference leaf accepts a plain string (not a leafref) so
     a `neighbor X { neighbor-group G; }` block is path-valid even
     before `neighbor-group G` has been declared — the same
     staging-friendly pattern other zebra-bgp-* augments use.";

  grouping bgp-neighbor-group-extension {
    description
      "Top-level `neighbor-group` list hung off `router bgp`.";
    list neighbor-group {
      key "name";
      ext:help "BGP neighbor-group (IOS-XR style)";
      description
        "List of BGP neighbor-groups configured on the local
         system, uniquely identified by name.";
      leaf name {
        ext:help "Neighbor-group name";
        type string;
        description
          "Name of the neighbor-group.";
      }
      leaf remote-as {
        ext:help "Remote AS number inherited by group members";
        type inet:as-number;
        description
          "AS number inherited by neighbors that reference this
           group. A `remote-as` set on the neighbor itself wins.";
      }

      leaf region-id {
        ext:help "RFC 9572 segmentation region identifier";
        type uint16;
        description
          "Mark this neighbor-group as an RFC 9572 region (Section 6.1).
           The value is a two-octet AS number used as the Source-AS-encoded
           Region ID carried in Per-Region I-PMSI (Type-9) routes that a
           Regional Border Router aggregates from, and re-originates into,
           this region. Absent means the group is not a region boundary.";
      }

      /* Per-neighbor knobs inheritable through the group. The same
       * explicit-wins rule applies to each: a statement on the
       * neighbor itself outranks the group's; absence of both means
       * the per-neighbor default. The transport / password /
       * allowas-in / as-override / remove-private-as /
       * enforce-first-as shapes are reused verbatim from the modules
       * that attach them to `neighbor`, so the two surfaces cannot
       * drift apart. */

      leaf passive {
        ext:help "Members only accept inbound sessions (never dial)";
        type boolean;
        description
          "Inherited passive mode. The flat-group spelling of the
           per-neighbor `transport passive-mode` leaf. Ignored by
           dynamic (listen-range) members, which are always passive.";
      }
      uses zbt:bgp-neighbor-transport-extension;
      uses zbp:bgp-neighbor-password-extension;
      uses zbai:bgp-neighbor-allowas-in-extension;
      uses zbao:bgp-neighbor-as-override-extension;
      uses zbrpa:bgp-neighbor-remove-private-as-extension;
      uses zbef:bgp-neighbor-enforce-first-as-extension;
      uses zbotc:bgp-neighbor-otc-local-role-extension;
      uses zbrs:bgp-neighbor-route-server-client-extension;
      /* TCP-AO for members, and — via a listen-range binding — for
         the whole range: a dynamic peer is materialized only after
         its SYN is accepted, so the MKT must already be on the
         listener, scoped to the prefix. */
      uses zbauth:bgp-tcp-ao-extension;
      container policy {
        ext:help "Route policy inherited by group members";
        description
          "Per-direction route-policy references, mirroring the
           per-neighbor `policy` container.";
        leaf in {
          ext:help "Inbound route policy";
          type string;
        }
        leaf out {
          ext:help "Outbound route policy";
          type string;
        }
      }
      container prefix-set {
        ext:help "Prefix filter inherited by group members";
        description
          "Per-direction prefix-set references, mirroring the
           per-neighbor `prefix-set` container.";
        leaf in {
          ext:help "Inbound prefix filter";
          type string;
        }
        leaf out {
          ext:help "Outbound prefix filter";
          type string;
        }
      }
      container route-reflector {
        ext:help "Route reflector parameters inherited by group members";
        description
          "Mirror of the per-neighbor `route-reflector` container
           (client leaf only — `cluster-id` stays per-neighbor).";
        leaf client {
          ext:help "Members are route-reflector clients";
          type boolean;
          description
            "Members are route-reflector clients.";
        }
      }

      list afi-safi {
        ext:help "Per-family settings inherited by members";
        key "name";
        description
          "Per-family toggles inherited by neighbors that reference
           this group. Tri-state per family: an entry with `enabled
           true` switches the family on for inheriting peers, an
           entry with `enabled false` switches it off (overriding
           the implicit IPv4-unicast default), and no entry leaves
           the peer's own setting (or the default) in effect. An
           `afi-safi` set explicitly on the neighbor itself wins.
           Like the per-neighbor knob, a change takes effect when
           the session next negotiates capabilities (`clear bgp`).";
        uses zas:afi-safi;
        leaf enabled {
          ext:help "Enable this address family for group members";
          type boolean;
          mandatory true;
          description
            "Whether this AFI,SAFI is enabled for peers inheriting
             from the group.";
        }
        leaf add-path {
          ext:help "Inherited per-family ADD-PATH mode";
          type enumeration {
            enum receive;
            enum send;
            enum send-receive;
          }
          description
            "Inherited RFC 7911 ADD-PATH mode, mirroring the
             per-neighbor `afi-safi <name> add-path` leaf. An
             `add-path` set explicitly on the neighbor itself wins.

             Defined here rather than by `uses`-ing the shared
             per-neighbor knob grouping because inheritance has to be
             implemented knob by knob — a leaf that appears in the
             schema but has no resolver would be accepted and silently
             ignored, which is the failure mode the knob module's own
             docs warn about. Same reason `next-hop-self` below is a
             hand-written mirror.

             Unlike `next-hop-self`, this is a capability carried in the
             OPEN, so a change bounces an Established member whose
             effective mode actually changed. It is the only way to give
             a listen-range group's dynamic members an ADD-PATH mode:
             they are materialized on accept, so no per-neighbor
             statement exists to carry one.";
        }
        leaf next-hop-self {
          ext:help "Inherited per-family next-hop-self";
          type boolean;
          description
            "Inherited per-family next-hop-self, mirroring the
             per-neighbor `afi-safi <name> next-hop-self` leaf.
             Applies to routes advertised after the change (no
             session bounce).";
        }
        uses zbak:bgp-neighbor-maximum-prefix;
      }
    }
  }

  grouping bgp-neighbor-attach-extension {
    description
      "Per-neighbor reference leaf attaching the neighbor to a
       neighbor-group.";
    leaf neighbor-group {
      ext:help "Neighbor-group to inherit attributes from";
      type string;
      description
        "Name of the `neighbor-group` whose attributes this
         neighbor inherits. Resolved at config commit; per-leaf
         values set on the neighbor override the group.";
    }
  }

  augment "/configure:set/config:router/bgp:bgp" {
    description
      "Attach the `neighbor-group` list to `router bgp` in the
       candidate-set subtree.";
    uses bgp-neighbor-group-extension;
  }

  augment "/configure:delete/config:router/bgp:bgp" {
    description
      "Same attachment for the delete subtree so
       `delete router bgp neighbor-group X` is path-valid.";
    uses bgp-neighbor-group-extension;
  }

  augment "/configure:set/config:router/bgp:bgp/bgp:neighbor" {
    description
      "Attach the `neighbor-group` reference leaf to each BGP
       neighbor entry in the candidate-set subtree.";
    uses bgp-neighbor-attach-extension;
  }

  augment "/configure:delete/config:router/bgp:bgp/bgp:neighbor" {
    description
      "Same attachment for the delete subtree.";
    uses bgp-neighbor-attach-extension;
  }
}

module zebra-afi-safi {
  yang-version "1";

  namespace "urn:ietf:params:xml:ns:yang:zebra-afi-safi";
  prefix "zas";

  organization
    "zebra-rs";

  contact
    "https://github.com/zebra-rs";

  description
    "zebra-rs's own address-family / sub-address-family definition,
     replacing the borrowed OpenConfig (AFI_SAFI_TYPE) and IANA
     (iana-bgp-types:afi-safi-type) afi-safi identities for the
     operator-facing config tree.

     Two flavors are provided as groupings supplying the `name` key of
     an `afi-safi` list:

       * `afi-safi`         — the full BGP set (ipv4, ipv6, vpnv4,
                              vpnv6, rtcv4, rtcv6, evpn, label-v4,
                              label-v6, flowspec-ipv4, flowspec-ipv6).
                              Used by `router bgp` (global + per-neighbor
                              afi-safi).
       * `afi-safi-unicast` — the unicast subset (ipv4, ipv6). Used by
                              `router isis` and the per-VRF BGP afi-safi
                              (which carries the same family names).

     The family names match the strings the Rust config layer parses
     (`Args::afi_safi`), so re-pointing a list's `name` leaf at one of
     these groupings is name-preserving and needs no runtime change.";

  grouping afi-safi {
    description
      "The `name` key for a BGP `afi-safi` list — the full set of
       families zebra-rs's BGP supports.";
    leaf name {
      ext:help "Address family / sub-address family";
      ext:no-sort "true";
      type enumeration {
        enum ipv4 {
          description "IPv4 unicast (AFI 1, SAFI 1).";
        }
        enum ipv6 {
          description "IPv6 unicast (AFI 2, SAFI 1).";
        }
        enum vpnv4 {
          description "MPLS-labeled VPN-IPv4 (AFI 1, SAFI 128).";
        }
        enum vpnv6 {
          description "MPLS-labeled VPN-IPv6 (AFI 2, SAFI 128).";
        }
        enum rtcv4 {
          description
            "IPv4 Route Target Constraint (AFI 1, SAFI 132).";
        }
        enum rtcv6 {
          description
            "IPv6 Route Target Constraint (AFI 2, SAFI 132).";
        }
        enum evpn {
          description "BGP EVPN (AFI 25, SAFI 70).";
        }
        enum label-v4 {
          description
            "IPv4 Labeled Unicast (AFI 1, SAFI 4); RFC 3107 / RFC 8277.";
        }
        enum label-v6 {
          description
            "IPv6 Labeled Unicast (AFI 2, SAFI 4); RFC 3107 / RFC 8277,
             incl. 6PE (RFC 4798).";
        }
        enum flowspec-ipv4 {
          description
            "IPv4 Flow Specification (AFI 1, SAFI 133, RFC 8955).";
        }
        enum flowspec-ipv6 {
          description
            "IPv6 Flow Specification (AFI 2, SAFI 133, RFC 8956).";
        }
        enum sr-policy-v4 {
          description "BGP SR Policy with IPv4 endpoint (AFI 1, SAFI 73).";
        }
        enum sr-policy-v6 {
          description "BGP SR Policy with IPv6 endpoint (AFI 2, SAFI 73).";
        }
        enum link-state {
          description "BGP Link-State (AFI 16388, SAFI 71, RFC 9552).";
        }
        enum mup {
          description
            "BGP Mobile User Plane (MUP), SAFI 85, draft-ietf-bess-mup-safi. A single
             config name that negotiates BOTH IPv4-MUP (AFI 1) and
             IPv6-MUP (AFI 2).";
        }
      }
      description
        "Address family / sub-address family this list entry configures.
         The `ext:no-sort` tag keeps CLI completion in this declared
         order rather than alphabetizing it.";
    }
  }

  grouping afi-safi-unicast {
    description
      "The `name` key for a unicast-only `afi-safi` list — used by
       IS-IS and the per-VRF BGP afi-safi.";
    leaf name {
      ext:help "Address family";
      type enumeration {
        enum ipv4 {
          description "IPv4 unicast.";
        }
        enum ipv6 {
          description "IPv6 unicast.";
        }
      }
      description
        "Address family this list entry configures.";
    }
  }
}

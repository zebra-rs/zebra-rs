module zebra-bgp-password {
  yang-version "1";

  namespace "urn:ietf:params:xml:ns:yang:zebra-bgp-password";
  prefix "zbp";

  import ietf-bgp {
    prefix bgp;
  }

  import config {
    prefix config;
  }

  import configure {
    prefix configure;
  }

  import extension {
    prefix ext;
  }

  organization
    "zebra-rs";

  contact
    "https://github.com/zebra-rs";

  description
    "FRR / IOS-XR style flat per-neighbor TCP MD5 password alias.

     Adds `password` directly under each BGP neighbor:

       router bgp {
         neighbor 10.0.0.5 {
           remote-as 65501;
           password secret;
         }
       }

     Functionally equivalent to the IETF-shaped `neighbor/tcp-md5/
     password` leaf from zebra-bgp-auth.yang; both lower onto the
     same runtime field (`peer.config.transport.md5_password`) and
     the same `setsockopt(TCP_MD5SIG)` site on the listener. The
     `tcp-md5` container path is retained for operators using the
     structured form; this module is for the flat CLI shortcut.";

  revision 2026-05-15 {
    description "Initial revision.";
    reference "FRR `neighbor X password`; Cisco IOS / IOS-XR equivalent; RFC 2385.";
  }

  grouping bgp-neighbor-password-extension {
    description
      "FRR-style flat password leaf on a BGP neighbor.";

    leaf password {
      ext:help "Shared MD5 secret (RFC 2385)";
      type string {
        length "1..80";
      }
      description
        "Shared MD5 secret. Max 80 bytes matches Linux's
         TCP_MD5SIG_MAXKEYLEN. Both peers MUST configure identical
         bytes or the TCP SYNs are silently dropped by the kernel
         and the session never establishes.

         Equivalent to `neighbor/tcp-md5/password` in
         zebra-bgp-auth.yang.";
      reference "RFC 2385";
    }
  }

  /* =========================================================
   * Augments into the zebra-rs configure tree
   * ========================================================= */

  augment "/configure:set/config:router"
        + "/bgp:bgp/bgp:neighbor" {
    description
      "Attach the flat password leaf to BGP neighbors in the
       candidate-set subtree.";
    uses bgp-neighbor-password-extension;
  }

  augment "/configure:delete/config:router"
        + "/bgp:bgp/bgp:neighbor" {
    description
      "Same attachment for the delete subtree so
       `delete router bgp neighbor X password` is path-valid.";
    uses bgp-neighbor-password-extension;
  }
}

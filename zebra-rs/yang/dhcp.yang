module dhcp {
  yang-version "1";

  namespace "urn:ietf:params:xml:ns:yang:zebra-dhcp";
  prefix "dhcp";

  import ietf-inet-types {
    prefix inet;
  }

  import extension {
    prefix ext;
  }

  description
    "VyOS-derived DHCP relay configuration, ported from the VyOS rolling
     interface definitions (vyos-1x interface-definitions/
     service_dhcp-relay.xml.in and service_dhcpv6-relay.xml.in).
     Enforced by the out-of-process insomnia daemon, which renders these
     trees into the config of its own relay agent (insomnia-dhcp-relay);
     zebra-rs owns only the schema and the config store.

     This module is a grouping library in the vrrp.yang / ipsec.yang
     style: config.yang instantiates the groupings under an
     insomnia-gated top-level `container service`, VyOS's own home for
     DHCP, so a VyOS `set service dhcp-relay …` line ports verbatim.
     The same groupings are instantiated again under a per-VRF `vrf`
     list, zebra-rs's `<feature> vrf <name>` convention; VyOS has no
     per-VRF relay.

     Scope: `service dhcp-relay` and `service dhcpv6-relay`. The DHCP
     server trees (`service dhcp-server`, `service dhcpv6-server`) land
     with insomnia's Kea backend. Deliberately not carried over: the v4
     relay's `interface` leaf, which VyOS deprecates in favour of
     `listen-interface` plus `upstream-interface`.

     Value-shape conventions follow vrrp.yang: no `pattern` statements
     on value leaves; interface references are plain `type string`, so
     an interface may be configured after the relay that names it.
     Defaults are not declared here: insomnia applies VyOS's defaults
     when rendering, so the JSON batch carries only what the operator
     set. The rules VyOS checks in verify() (a server is required,
     listen and upstream interfaces come together, each DHCPv6 upstream
     interface needs an address) are applied by insomnia, which skips
     what fails them with a warning.";

  revision "2026-11-08" {
    description
      "Replaced the unused IETF dhc draft model (2016-08-25, mounted at
       `system dhcp`) with the VyOS-derived relay trees.";
  }

  // ---------------------------------------------------------------
  // service dhcp-relay — vyos-1x service_dhcp-relay.xml.in
  // ---------------------------------------------------------------

  grouping dhcp-relay {
    leaf disable {
      ext:help "Disable instance";
      type empty;
    }
    leaf-list listen-interface {
      ext:help "Interface for DHCP Relay Agent to listen for requests";
      type string;
    }
    leaf-list upstream-interface {
      ext:help "Interface for DHCP Relay Agent forward requests out";
      type string;
    }
    leaf-list server {
      ext:help "DHCP server address";
      type inet:ipv4-address;
    }
    container relay-options {
      ext:help "Relay options";
      leaf hop-count {
        ext:help "Policy to discard packets that have reached specified hop-count (VyOS default: 10)";
        type uint8 {
          range "1..255";
        }
      }
      leaf max-size {
        ext:help "Maximum packet size to send to a DHCPv4/BOOTP server (VyOS default: 576)";
        type uint16 {
          range "64..1400";
        }
      }
      leaf relay-agents-packets {
        ext:help "Policy to handle incoming DHCPv4 packets which already contain relay agent options (VyOS default: forward)";
        type enumeration {
          enum append {
            description "Append own relay options to packet";
          }
          enum replace {
            description "Replace existing agent option field";
          }
          enum forward {
            description "Forward the packet unchanged";
          }
          enum discard {
            description "Discard the packet";
          }
        }
      }
    }
  }

  // ---------------------------------------------------------------
  // service dhcpv6-relay — vyos-1x service_dhcpv6-relay.xml.in
  // ---------------------------------------------------------------

  grouping dhcpv6-relay {
    leaf disable {
      ext:help "Disable instance";
      type empty;
    }
    list listen-interface {
      ext:help "Interface for DHCPv6 Relay Agent to listen for requests";
      key "name";
      leaf name {
        ext:help "Interface name";
        type string;
      }
      leaf address {
        ext:help "IPv6 address on listen-interface listen for requests on";
        type inet:ipv6-address;
      }
    }
    leaf max-hop-count {
      ext:help "Maximum hop count for which requests will be processed (VyOS default: 10)";
      type uint8 {
        range "1..255";
      }
    }
    list upstream-interface {
      ext:help "Interface for DHCPv6 Relay Agent forward requests out";
      key "name";
      leaf name {
        ext:help "Interface name";
        type string;
      }
      leaf-list address {
        ext:help "IPv6 address to forward requests to";
        type inet:ipv6-address;
      }
    }
    leaf use-interface-id-option {
      ext:help "Option to set DHCPv6 interface-ID option";
      type empty;
    }
  }
}

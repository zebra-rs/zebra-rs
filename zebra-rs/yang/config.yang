module config {
  yang-version "1";

  namespace "urn:ietf:params:xml:ns:yang:zebra";
  prefix "config";

  import ietf-inet-types {
    prefix inet;
  }

  import ietf-yang-types {
    prefix yang;
  }

  import extension {
    prefix ext;
  }

  import zebra-features {
    prefix feat;
  }

  import dhcp {
    prefix dhcp;
  }

  import firewall {
    prefix fw;
  }

  import ipsec {
    prefix ipsec;
  }

  import vrrp {
    prefix vrrp;
  }

  import ietf-bgp {
    prefix bgp;
  }

  import ietf-bgp-policy {
    prefix policy;
  }

  import zebra-bgp-auth {
    prefix zba;
  }

  import zebra-bgp-sharding {
    prefix zbsh;
  }

  import zebra-bgp-vrf {
    prefix zbv;
  }

  import zebra-bgp-evpn {
    prefix zbe;
  }

  import zebra-bgp-mup-controller {
    prefix zbmupc;
  }

  import zebra-bgp-redistribute {
    prefix zbr;
  }

  import zebra-bgp-table-map {
    prefix zbtm;
  }

  import zebra-bgp-multipath {
    prefix zbmp;
  }

  import zebra-bgp-bestpath {
    prefix zbbp;
  }

  import zebra-bgp-graceful-restart {
    prefix zbgr;
  }

  import zebra-bgp-suppress-fib-pending {
    prefix zbsfp;
  }

  import zebra-bgp-transport {
    prefix zbt;
  }

  // Temporarily disabled: the embedded Lua scripting engine is turned
  // off for now (the `lua` build feature defaults off). This bootstrap
  // import is the only thing that pulls zebra-bgp-lua's augments into
  // the configure tree, so commenting it out removes `router bgp
  // lua-script / lua-map / loc-rib-hook / adj-rib-out-hook` from the
  // schema. Re-enable together with the `lua` feature (and uncomment the
  // schema body in zebra-bgp-lua.yang).
  /*
  import zebra-bgp-lua {
    prefix zbl;
  }
  */

  import zebra-bgp-password {
    prefix zbp;
  }

  import zebra-bgp-bfd {
    prefix zbb;
  }

  import zebra-ospf-bfd {
    prefix zob;
  }

  import zebra-ospf-auth-simple {
    prefix zoas;
  }

  import zebra-ospf-auth-md5 {
    prefix zoam;
  }

  import zebra-ospf-auth-trailer {
    prefix zoat;
  }

  import zebra-ospfv3-auth {
    prefix zo3a;
  }

  import zebra-ospf-tracing {
    prefix zotr;
  }

  import zebra-isis-tracing {
    prefix zitr;
  }

  import zebra-pim-tracing {
    prefix zptr;
  }

  import zebra-bgp-color-policy {
    prefix zbcp;
  }

  import zebra-bgp-sr-policy {
    prefix zbsp;
  }

  import zebra-bgp-flowspec {
    prefix zbfs;
  }

  import zebra-bgp-allowas-in {
    prefix zbai;
  }

  import zebra-bgp-as-override {
    prefix zbao;
  }

  import zebra-bgp-as-sets-withdraw {
    prefix zbasw;
  }

  import zebra-bgp-remove-private-as {
    prefix zbrpa;
  }

  import zebra-bgp-enforce-first-as {
    prefix zbef;
  }
  import zebra-bgp-otc {
    prefix zbotc;
  }
  import zebra-bgp-route-server {
    prefix zbrs;
  }
  import zebra-bgp-capability {
    prefix zbcap;
  }
  import zebra-bgp-unknown-attr {
    prefix zbua;
  }
  import zebra-bgp-pic-retention {
    prefix zbpic;
  }

  import zebra-bgp-local-as {
    prefix zbla;
  }

  import zebra-bgp-timer {
    prefix zbtm;
  }

  import zebra-bgp-tracing {
    prefix zbtr;
  }

  import zebra-rib-tracing {
    prefix zrft;
  }

  import openconfig-isis-types {
    prefix isis;
  }
  import zebra-afi-safi {
    prefix zas;
  }

  import config-static {
    prefix static;
  }

  import vty {
    prefix vty;
  }

  typedef vrf-route-target {
    type string {
      pattern
          '(6553[0-5]|655[0-2][0-9]|65[0-4][0-9]{2}|'
        + '6[0-4][0-9]{3}|[1-5][0-9]{4}|[1-9][0-9]{0,3}|0)'
        + ':'
        + '(429496729[0-5]|42949672[0-8][0-9]|'
        + '4294967[01][0-9]{2}|429496[0-6][0-9]{3}|'
        + '42949[0-5][0-9]{4}|4294[0-8][0-9]{5}|'
        + '429[0-3][0-9]{6}|42[0-8][0-9]{7}|'
        + '4[01][0-9]{8}|[1-3][0-9]{9}|'
        + '[1-9][0-9]{0,8}|0)'
        + '|'
        + '((25[0-5]|2[0-4][0-9]|1[0-9]{2}|[1-9]?[0-9])\.){3}'
        + '(25[0-5]|2[0-4][0-9]|1[0-9]{2}|[1-9]?[0-9])'
        + ':'
        + '(6553[0-5]|655[0-2][0-9]|65[0-4][0-9]{2}|'
        + '6[0-4][0-9]{3}|[1-5][0-9]{4}|[1-9][0-9]{0,3}|0)'
        + '|'
        + '(429496729[0-5]|42949672[0-8][0-9]|'
        + '4294967[01][0-9]{2}|429496[0-6][0-9]{3}|'
        + '42949[0-5][0-9]{4}|4294[0-8][0-9]{5}|'
        + '429[0-3][0-9]{6}|42[0-8][0-9]{7}|'
        + '4[01][0-9]{8}|[1-3][0-9]{9}|'
        + '[1-9][0-9]{0,8}|0)'
        + ':'
        + '(6553[0-5]|655[0-2][0-9]|65[0-4][0-9]{2}|'
        + '6[0-4][0-9]{3}|[1-5][0-9]{4}|[1-9][0-9]{0,3}|0)';
    }
    description
      "BGP/MPLS VPN Route Target in operator-friendly notation
       (no leading type-number prefix). Three encodings are accepted:

         Type 0:  2-byte-ASN:4-byte-number    e.g. 65000:100
         Type 1:  IPv4-address:2-byte-number  e.g. 192.0.2.1:100
         Type 2:  4-byte-ASN:2-byte-number    e.g. 4200000000:100

       Disambiguation between Type 0 and Type 2 is by the magnitude
       of the first field: <= 65535 means Type 0, otherwise Type 2.
       Type 1 is recognised by the dotted-quad in the first field.

       This differs from RFC 8294 / ietf-routing-types route-target,
       which prefixes each value with the type number (0:65000:100).";
    reference
      "RFC 4360: BGP Extended Communities Attribute
       RFC 4364: BGP/MPLS IP Virtual Private Networks (VPNs)
       RFC 5668: 4-Octet AS Specific BGP Extended Community";
  }

  grouping isis-redist-common {
    description
      "Common per-source knobs for IS-IS redistribution. Reused by
       every `container redistribute/<source>` entry under
       `router isis / afi-safi`.";
    leaf policy {
      ext:help "Route-policy name for redistribution filter";
      // Name of a top-level `policy` (the /policy list). Held as a
      // plain string (not a leafref) so the redistribute config can
      // be staged before the policy is committed — same convention
      // as `router isis / segment-routing / srv6 / locator`.
      type string;
    }
    leaf metric {
      ext:help "Static metric for redistributed routes";
      type uint32 {
        range "0..16777215";
      }
      description
        "Static metric override for redistributed routes. When omitted,
         the source RIB cost is used (subject to `metric-type` below).";
    }
    leaf level {
      ext:help "IS-IS level for originated reachability";
      type enumeration {
        enum level-1;
        enum level-2;
        enum level-1-2;
      }
      default "level-2";
      description
        "Target IS-IS level for the originated reachability TLV. Default
         matches IOS-XR.";
    }
    leaf metric-type {
      ext:help "IS-IS internal/external metric-type (RFC 5305)";
      type enumeration {
        enum internal;
        enum external;
        enum rib-metric-as-internal;
        enum rib-metric-as-external;
      }
      default "internal";
      description
        "RFC 5305 I/E bit selection. `rib-metric-as-*` lifts the RIB
         cost into the IS-IS metric instead of using a static value.";
    }
  }

  grouping isis-redist-ospf-match {
    description
      "OSPF-source filter for `redistribute ospf`. IOS-XR allows only
       one of {internal, external, nssa-external} per redistribute
       entry — repeating the command overwrites rather than stacks.
       Modeled as a leaf-list for shape simplicity; the IS-IS callback
       enforces the single-value rule at commit time.";
    container match {
      ext:help "OSPF route-type filter for redistribution";
      leaf-list type {
        ext:help "OSPF route type to redistribute";
        type enumeration {
          enum internal;
          enum external;
          enum nssa-external;
        }
      }
    }
  }

  grouping vrf-route-target-policy {
    description
      "Per-address-family RT import/export sets attached to a VRF.";
    container route-target {
      ext:help "Route Target import/export sets for this VRF";
      leaf-list import {
        ext:help "Route Targets imported into this VRF";
        type vrf-route-target;
        description
          "Route Targets accepted into this VRF. A VPN route is
           imported if any of its attached RTs matches an entry here.";
      }
      leaf-list export {
        ext:help "Route Targets attached to exported routes";
        type vrf-route-target;
        description
          "Route Targets attached to routes exported from this VRF.
           Every locally-originated VPN route is tagged with all
           entries listed here.";
      }
    }
  }

  grouping config {
    uses "zba:key-chains-group";

    container logging {
      ext:help "Logging configuration";
      leaf output {
        ext:help "Log output destination";
        type enumeration {
          enum stdout;
          enum syslog;
          enum file;
        }
      }
    }

    list bridge {
      ext:help "Bridge interface configuration";
      ext:sort "100";
      key "name";
      leaf name {
        ext:help "Bridge name";
        type string;
      }
      leaf address-gen-mode {
        ext:help "IPv6 address generation mode";
        type enumeration {
          enum none;
          enum eui64;
          enum random;
          enum stable-secret;
        }
      }
    }

    list vxlan {
      ext:help "VXLAN interface configuration";
      ext:sort "90";
      key "name";
      leaf name {
        ext:help "VXLAN interface name";
        type string;
      }
      leaf local-address {
        ext:help "VXLAN local tunnel (VTEP) address";
        type union {
          type inet:ipv4-address;
          type inet:ipv6-address;
        }
      }
      leaf vni {
        ext:help "VXLAN Network Identifier (VNI)";
        ext:sort "5";
        mandatory true;
        type uint32;
      }
      leaf dest-port {
        ext:help "VXLAN UDP destination port";
        type uint16;
      }
      leaf address-gen-mode {
        ext:help "IPv6 address generation mode";
        type enumeration {
          enum none;
          enum eui64;
          enum random;
          enum stable-secret;
        }
      }
      leaf bridge {
        ext:help "Bridge master to enslave this VXLAN device";
        ext:dynamic "rib:bridge";
        type leafref {
          path "/bridge/name";
        }
        description
          "Enslave this VXLAN device to the named bridge master,
           equivalent to `ip link set <name> master <bridge>`. Reuses
           the same staged bridge-bind as `interface <name> bridge
           <bridge>` (applied once both the VXLAN and the bridge exist,
           so config order is free), and the VXLAN bridge-slave defaults
           are applied automatically: addrgenmode none (the VXLAN
           creation default) plus `neigh_suppress on` and `learning off`
           on the bridge port (set by `vxlan_bridge_port_defaults` when
           the VXLAN gains a master). Omitted means the VXLAN is not a
           bridge port.";
      }
      leaf vrf {
        ext:help "Tenant VRF this device is an L3VNI for (EVPN IRB)";
        ext:dynamic "rib:vrf";
        type leafref {
          path "/vrf/name";
        }
        description
          "Bind this VXLAN device to a tenant VRF as an EVPN symmetric-IRB
           L3VNI (RFC 9135 / RFC 8365). A VXLAN frame received on this VNI
           routes its inner IP in the VRF's FIB (instead of bridging into
           an L2 domain), and the VRF's Type-5 routes are VXLAN-encapsulated
           toward the remote VTEP. Requires `router bgp vrf <name> evpn
           advertise-ipv4/ipv6` and matching `encapsulation vxlan`.";
      }
      leaf router-mac {
        ext:help "Router-MAC for this L3VNI (EVPN IRB inner rewrite)";
        type yang:mac-address;
        description
          "This PE's router-MAC for the L3VNI. On ingress the inner
           Ethernet is rewritten with the remote PE's router-MAC before
           encapsulation; on egress a frame whose inner destination matches
           this MAC is routed in the bound VRF. Defaults to the VRF master
           device MAC when unset.";
      }
    }

    list vlan {
      ext:help "VLAN sub-interface configuration";
      // Sorted after bridge (100), vxlan (90) and vrf (30) — a VLAN's
      // parent may itself be a config-created device (a bridge SVI) —
      // and before interface (20). Note that `interface` addresses on
      // a device created in the same commit are dropped today (the
      // address exec is immediate while device creation lands at
      // CommitEnd + a netlink echo later) — the same pre-existing
      // limitation as bridge/vxlan; VRF and bridge binds are staged
      // (`pending_vrf_bind` / `pending_bridge_bind`) and do apply.
      ext:sort "25";
      key "name";
      description
        "An 802.1Q VLAN sub-interface created and owned by zebra-rs,
         equivalent to `ip link add link <interface> name <name> type
         vlan id <vlan-id>`. Unlike the `interface` list — which only
         attaches configuration to kernel devices that already exist —
         each entry here creates the kernel device, and deleting the
         entry deletes it. The name is a free-form label (`eth0.100` is
         only a convention); the parent and VLAN id come exclusively
         from the two mandatory leaves. Creation is deferred until the
         parent exists in the kernel and replayed when it (re)appears —
         the kernel removes VLAN children with a deleted parent, so on
         its return they are created again.";
      leaf name {
        ext:help "VLAN interface name";
        type string;
      }
      leaf interface {
        ext:help "Parent interface the VLAN rides on";
        ext:sort "5";
        ext:dynamic "rib:interface";
        mandatory true;
        type string;
        description
          "The lower device this VLAN sub-interface is stacked on (the
           kernel's IFLA_LINK). May name an interface that does not
           exist yet — creation is staged until it appears.";
      }
      leaf vlan-id {
        ext:help "802.1Q VLAN id";
        mandatory true;
        type uint16 {
          range "1..4094";
        }
        description
          "The 802.1Q tag. Changing it (or the parent) on an existing
           entry re-creates the kernel device — the kernel does not
           allow either to change on a live link.";
      }
    }

    container mpls {
      ext:help "MPLS forwarding configuration";
      description
        "Global MPLS forwarding attributes.";
      container ttl {
        ext:help "MPLS label TTL processing";
        // RFC 3443 label-stack TTL model. `pipe` (default) hides the LSP
        // from the payload: imposition seeds the outer label TTL with 255
        // and disposition discards it, leaving the inner IP TTL untouched.
        // `uniform` exposes the LSP end to end: imposition seeds the label
        // TTL from the inner IP TTL and disposition copies the (decremented)
        // label TTL back into the inner IP header on pop-to-IP. Honored by
        // the cradle eBPF data plane (Nexthop.mpls_pipe_ttl at imposition,
        // Ilm.ttl_uniform at disposition); the kernel FIB is unaffected.
        leaf propagate {
          ext:help "MPLS TTL propagation model (pipe hides the LSP, uniform exposes it)";
          type enumeration {
            enum pipe;
            enum uniform;
          }
          default "pipe";
          description
            "RFC 3443 label TTL model. `pipe` (default) hides the LSP hop
             count from the payload; `uniform` propagates it end to end.";
        }
        // The IOS forwarded/local split (`mpls ip propagate-ttl [forwarded |
        // local]`). `propagate` above is the FORWARDED (transit) model, teed
        // to the cradle data plane — cradle only ever imposes forwarded
        // traffic. This leaf is the LOCAL model, for the router's own
        // (locally-originated) MPLS traffic, which the host kernel imposes
        // (the lwtunnel MPLS encap routes zebra installs), governed by the
        // global `net.mpls.ip_ttl_propagate` sysctl. Split so an operator can
        // hide the core from customer traceroutes (forwarded `pipe`) while
        // still seeing the LSP from the PE itself (local `uniform`).
        leaf propagate-local {
          ext:help "MPLS TTL model for locally-originated traffic (kernel imposition)";
          type enumeration {
            enum pipe;
            enum uniform;
          }
          default "uniform";
          description
            "RFC 3443 label TTL model for LOCALLY-ORIGINATED traffic, applied
             to the host kernel's MPLS imposition via
             `net.mpls.ip_ttl_propagate`. `uniform` (default, the kernel
             default) exposes the LSP to the router's own traceroute; `pipe`
             hides it. Global only — the kernel knob has no per-VRF form.";
        }
      }
      container label-range {
        ext:help "MPLS label ranges";
        // The labels handed out dynamically: BGP's label blocks
        // (docs/design/mpls-label-allocation.md §3, §8). Segment-routing
        // blocks inside it are stepped around. A change applies to blocks
        // handed out from then on; one already outside the new range stays
        // until its owner gives it back.
        container dynamic {
          ext:help "Labels handed out dynamically (BGP's label blocks)";
          leaf start {
            ext:help "First dynamic label (default 24000)";
            type uint32 {
              range "16..1048574";
            }
          }
          leaf end {
            ext:help "Last dynamic label (default 1048574, the last the kernel installs)";
            type uint32 {
              range "16..1048574";
            }
          }
        }
      }
    }

    container system {
      ext:help "System configuration";
      description
        "System group configuration.";

      leaf hostname {
        ext:help "System host name";
        // RFC 1123-ish charset. Deliberately strict: the value is
        // surfaced to the vty shell and interpolated into the prompt
        // eval line (see vtyhelper), so quotes / spaces / shell
        // metacharacters must be impossible by construction.
        //
        // The pattern cannot count, nor tell `r1..x` and `r1-` from a
        // name: a commit also checks that the value is one the kernel
        // takes (`config::check`, `rib::hostname::valid`).
        type string {
          pattern "[A-Za-z0-9][A-Za-z0-9.-]*";
        }
        description
          "The name of the host. This name can be a single domain label or the
           fully qualified domain name of the host: at most 64 characters,
           in labels of letters, digits and hyphens.

           By itself this names the router inside zebra-rs: the vty
           prompt, `show hostname`, the DHCP client's host name option.
           With `--feature insomnia`, and zebra-rs running in the default
           network namespace, it is also made the system's host name: the
           kernel's and the one in /etc/hostname. Deleting it gives the
           system back the name it had before.";
      }
      // Global Router ID, `system router-id A.B.C.D` (the equivalent
      // of FRR/zebra's top-level `router-id`). When set it overrides
      // the automatic pick (first non-localhost IPv4, loopbacks
      // preferred — see `rib/router_id.rs`) and is pushed to protocol
      // subscribers via `RibRx::RouterIdUpdate`; deleting it falls
      // back to the automatic pick. Protocol-local identifiers
      // (`router bgp global router-id`, `router ospf router-id`, …)
      // still apply on their own instances.
      leaf router-id {
        ext:help "Global router identifier";
        type inet:ipv4-address;
      }
      // The zebra-rs side of the cradle-rs eBPF data-plane integration:
      // while the tee is active, every route zebra-rs installs is teed to
      // cradle in addition to the kernel, and cradle's datapath MAC
      // learning is fed back into EVPN (see `rib/inst.rs`). The tee is
      // active when either switch is on: `system ebpf enabled` (managed
      // engine) implies it, and this container's `enabled` activates it
      // standalone for an externally-run engine.
      container cradle {
        ext:help "cradle eBPF data-plane integration";
        leaf enabled {
          ext:help "Enable the cradle eBPF data-plane tee";
          type boolean;
          description
            "Activate the cradle eBPF data-plane tee without a managed
             engine — the switch for teeing to an externally-run cradle.
             (`system ebpf enabled` already implies the tee for the engine
             it manages, so this leaf is not needed there.) The endpoint is
             `system cradle grpc-endpoint` if set, otherwise the default
             `unix:cradle/grpc` (a Linux abstract socket, matching cradle's
             own default).";
        }
        // gRPC endpoint of the cradle eBPF data plane to tee FIB route
        // installs to (e.g. `unix:/run/cradle.sock` or `127.0.0.1:50151`).
        // Optional override for the default `unix:cradle/grpc`; it only takes
        // effect while the tee is enabled — on its own it does not enable it.
        // Shared with `system ebpf`: a spawned engine serves its gRPC API on
        // this same endpoint.
        leaf grpc-endpoint {
          ext:help "cradle eBPF data-plane gRPC endpoint";
          type string;
        }
      }
      // SONiC's Forwarding Plane Manager southbound. When enabled, FIB
      // route installs are teed to `fpmsyncd` over TCP in addition to the
      // kernel, which is how routes reach APPL_DB -> orchagent -> SAI on a
      // SONiC switch. The kernel install is unaffected: SONiC expects both
      // a kernel route and an ASIC route for every prefix.
      //
      // The leaf names mirror FRR's own `fpm address A.B.C.D [port N]`, so
      // the shape is familiar to anyone who has configured the FRR side.
      container fpm {
        ext:help "SONiC FPM (fpmsyncd) southbound";
        leaf enabled {
          ext:help "Enable the SONiC FPM tee";
          type boolean;
          description
            "Activate teeing of FIB route installs to fpmsyncd. The
             endpoint is `system fpm address` (default 127.0.0.1) and
             `system fpm port` (default 2620, fpmsyncd's well-known
             port). fpmsyncd is the server side of FPM — zebra-rs dials
             out to it.";
        }
        leaf address {
          ext:help "fpmsyncd address to connect to";
          type inet:ip-address;
          description
            "Address fpmsyncd listens on. Defaults to 127.0.0.1, which is
             where it runs in SONiC's bgp container. Changing it while the
             tee is enabled reconnects to the new endpoint and replays the
             full table, as FPM requires after any reconnect.";
        }
        leaf port {
          ext:help "fpmsyncd TCP port";
          type uint16;
          description
            "Defaults to 2620 (FPM_DEFAULT_PORT). fpmsyncd's listen port
             is not configurable on its side, so this exists mainly for
             test rigs that interpose a proxy.";
        }
      }
      // The engine-lifecycle half of the eBPF data-plane integration:
      // when enabled, zebra-rs spawns the cradle daemon as a managed,
      // supervised child process (adopting an instance already listening
      // on the endpoint instead of spawning a second one) and implies the
      // FIB tee — a managed engine is always programmed with zebra-rs's
      // routing state once it is up. Interfaces join the data plane via
      // `interface <if-name> ebpf enabled`; with no ports attached the
      // engine forwards nothing.
      container ebpf {
        ext:help "eBPF data-plane engine (managed cradle process)";
        leaf enabled {
          ext:help "Spawn and supervise the cradle eBPF data-plane engine";
          type boolean;
          description
            "When true, zebra-rs launches the cradle eBPF data plane as a
             managed child process, restarts it on failure, and implies the
             FIB tee — routes, ILMs, SRv6 SIDs and EVPN state are programmed
             into the managed engine with no separate `system cradle
             enabled`. The child serves its gRPC API on `system cradle
             grpc-endpoint` if set, otherwise on the default
             `unix:cradle/grpc` abstract socket; a cradle instance already
             listening there is adopted rather than duplicated. When false
             or unset no process is managed — an externally-run cradle can
             still be teed to through `system cradle enabled`.";
        }
        leaf mode {
          ext:help "Single-hook datapath benchmark mode (tc-only|xdp-only)";
          type enumeration {
            enum tc-only;
            enum xdp-only;
          }
          description
            "Performance-investigation knob (docs/design/xdp-tc-fast-path.md):
             restrict the managed cradle engine to plain IPv4 L3 forwarding
             through a SINGLE eBPF hook, so each hook's cost can be measured in
             isolation. `tc-only` attaches only the TC classifier (cradle_tc,
             which then runs an L3-only fast path); `xdp-only` attaches only a
             dedicated XDP forwarder (cradle_xdp_l3). Also defaults the IPv4 FIB
             engine to DIR-24-8. Passed to the engine as `--ebpf-mode` at spawn,
             so a change restarts the managed child. Non-L3 features (NAT,
             policy, overlay, L2) are unsupported while set — do not use in
             production. When unset the full XDP+TC pipeline runs as normal.";
        }
      }
      container etcd {
        ext:help "etcd datastore configuration";
        list endpoints {
          ext:help "etcd server endpoint";
          key "url";
          leaf url {
            ext:help "etcd endpoint URL";
            type string;
          }
        }
        leaf path {
          ext:help "etcd key path prefix";
          type string;
        }
      }
    }

    container vty {
      ext:help "VTY (CLI) configuration";
      uses "vty:vty";
    }

    container bfd {
      ext:help "BFD (Bidirectional Forwarding Detection) configuration";
      leaf tracing {
        ext:help "Enable conditional BFD task tracing";
        type boolean;
        description
          "Enable conditional tracing for the BFD task. When true, the
           BFD task emits its info / warn / debug traces (session FSM,
           packet handling, Echo reflector lifecycle); when false
           (the default) they are suppressed. Runtime toggle, no
           restart needed: `set bfd tracing true`.";
      }
    }

    container affinity-map {
      ext:help "Named affinity (admin-group) table";
      // Global named affinity table (RFC 7308 Extended Admin Group).
      // Each entry binds an operator-friendly name to a bit position
      // in the 256-bit bitmap. Shared by every IGP: per-link
      // `affinity` leaf-lists (under `router isis` / `router ospf` /
      // `router ospfv3` interfaces) and per-flex-algo include-any /
      // include-all / exclude-any constraints reference these names.
      // Each protocol task keeps its own copy fed by the config
      // broadcast.
      list affinity {
        ext:help "Named affinity (admin-group) entry";
        key "name";
        leaf name {
          ext:help "Affinity name";
          type string;
        }
        leaf bit-position {
          ext:help "Bit index in the Extended Admin Group (0-255)";
          type uint16 { range "0..255"; }
          mandatory true;
          description
            "Bit index in the 256-bit Extended Admin Group
             (RFC 7308). The on-the-wire bitmap is the union of
             bit positions referenced by all `affinity` names
             attached to a given link, advertised inside the
             ASLA sub-TLV (RFC 9479 for IS-IS, RFC 9492 for OSPF)
             when at least one flex-algo references the attribute.";
        }
      }
    }

    container srlg {
      ext:help "Shared Risk Link Group configuration";
      description
        "Global Shared Risk Link Group (SRLG) table. Each named group
         binds an operator-friendly identifier to the 32-bit SRLG value
         advertised by the IGPs (IS-IS TLV 138/139, RFC 5307/6119;
         OSPF SRLG sub-TLV, RFC 9492). Each IGP resolves its
         per-interface SRLG name references against this table when
         building LSPs/LSAs.";

      list group {
        ext:help "Named SRLG group";
        key "name";
        description
          "Named SRLG group. The name is the handle used by the
           per-interface `srlg` leaf-list under an IGP's interface
           subtree; the value is the 32-bit identifier emitted on the
           wire.";
        leaf name {
          ext:help "SRLG group name";
          type string;
          description
            "Operator-assigned SRLG group identifier.";
        }
        leaf value {
          ext:help "32-bit SRLG value advertised by IGPs";
          type uint32;
          mandatory true;
          description
            "32-bit SRLG value advertised in IGP TE extensions. Two
             links share fate (are in the same shared risk group) iff
             they carry a common value here. The numeric space is
             operator-defined; uniqueness is not enforced — different
             group names may intentionally share a value (e.g. as
             aliases) or accidentally collide.";
        }
      }
    }

    container router {
      ext:help "Router configuration";
      uses "ietf-bgp:bgp";
      // uses "policy:defined-sets";
      container ospf {
        ext:help "OSPFv2 configuration";
        presence "Enables configuration of OSPFv2";
        leaf router-id {
          ext:help "OSPF router identifier";
          type inet:ipv4-address;
        }
        // Instance-level redistribute into Type-5 AS-External LSAs
        // (RFC 2328 §12.4.5). Flooded AS-wide into all normal areas.
        // Per-area NSSA redistribution is under list area / redistribute.
        container redistribute {
          ext:help "Redistribute routes into OSPF";
          container connected {
            ext:help "Redistribute connected routes";
            presence "Redistribute connected routes as Type-5 AS-External LSAs";
            leaf metric {
              ext:help "Metric for redistributed routes";
              type uint32 {
                range "0..16777214";
              }
              default 20;
            }
            leaf metric-type {
              ext:help "OSPF external metric type (1 or 2)";
              type enumeration {
                enum type-1;
                enum type-2;
              }
              default type-2;
            }
            leaf route-map {
              ext:help "Filter/modify redistributed routes via a named policy-list";
              type string;
            }
          }
          container static {
            ext:help "Redistribute static routes";
            presence "Redistribute static routes as Type-5 AS-External LSAs";
            leaf metric {
              ext:help "Metric for redistributed routes";
              type uint32 {
                range "0..16777214";
              }
              default 20;
            }
            leaf metric-type {
              ext:help "OSPF external metric type (1 or 2)";
              type enumeration {
                enum type-1;
                enum type-2;
              }
              default type-2;
            }
            leaf route-map {
              ext:help "Filter/modify redistributed routes via a named policy-list";
              type string;
            }
          }
          container kernel {
            ext:help "Redistribute kernel routes";
            presence "Redistribute kernel routes as Type-5 AS-External LSAs";
            leaf metric {
              ext:help "Metric for redistributed routes";
              type uint32 {
                range "0..16777214";
              }
              default 20;
            }
            leaf metric-type {
              ext:help "OSPF external metric type (1 or 2)";
              type enumeration {
                enum type-1;
                enum type-2;
              }
              default type-2;
            }
            leaf route-map {
              ext:help "Filter/modify redistributed routes via a named policy-list";
              type string;
            }
          }
          container isis {
            ext:help "Redistribute IS-IS routes";
            presence "Redistribute IS-IS routes as Type-5 AS-External LSAs";
            leaf metric {
              ext:help "Metric for redistributed routes";
              type uint32 {
                range "0..16777214";
              }
              default 20;
            }
            leaf metric-type {
              ext:help "OSPF external metric type (1 or 2)";
              type enumeration {
                enum type-1;
                enum type-2;
              }
              default type-2;
            }
            leaf route-map {
              ext:help "Filter/modify redistributed routes via a named policy-list";
              type string;
            }
          }
          container bgp {
            ext:help "Redistribute BGP routes";
            presence "Redistribute BGP routes as Type-5 AS-External LSAs";
            leaf metric {
              ext:help "Metric for redistributed routes";
              type uint32 {
                range "0..16777214";
              }
              default 20;
            }
            leaf metric-type {
              ext:help "OSPF external metric type (1 or 2)";
              type enumeration {
                enum type-1;
                enum type-2;
              }
              default type-2;
            }
            leaf route-map {
              ext:help "Filter/modify redistributed routes via a named policy-list";
              type string;
            }
          }
          list table {
            ext:help "Redistribute routes from a kernel routing table";
            // FRR `redistribute table (1-65535)`: import routes the
            // kernel holds in a non-main routing table (installed
            // externally, e.g. `ip route ... table N`) as Type-5
            // AS-External LSAs. Keyed by table id so several tables
            // can redistribute at once, each with its own metric /
            // metric-type / route-map.
            key "id";
            leaf id {
              ext:help "Kernel routing table ID";
              type uint32 {
                range "1..65535";
              }
            }
            leaf metric {
              ext:help "Metric for redistributed routes";
              type uint32 {
                range "0..16777214";
              }
              default 20;
            }
            leaf metric-type {
              ext:help "OSPF external metric type (1 or 2)";
              type enumeration {
                enum type-1;
                enum type-2;
              }
              default type-2;
            }
            leaf route-map {
              ext:help "Filter/modify redistributed routes via a named policy-list";
              type string;
            }
          }
        }
        // FRR-parity `default-information originate`: advertise a
        // Type-5 default route. Without `always` it is originated
        // only while a non-OSPF default route sits in the RIB
        // (tracked via the RIB default-route watch); `always`
        // originates unconditionally. Metric defaults to 10 (FRR
        // convention for the originated default; redistribute uses
        // 20), E2 semantics.
        container default-information {
          ext:help "Control default-route origination";
          container originate {
            ext:help "Originate a default route";
            presence "Originate a Type-5 default route";
            leaf always {
              ext:help "Originate default even without one in RIB";
              type boolean;
              default false;
            }
            leaf metric {
              ext:help "Metric for the originated default route";
              type uint32 {
                range "0..16777214";
              }
              default 10;
            }
            leaf metric-type {
              ext:help "OSPF external metric type (1 or 2)";
              type enumeration {
                enum type-1;
                enum type-2;
              }
              default type-2;
            }
          }
        }
        list area {
          ext:help "OSPF area";
          // Area key accepts either a plain decimal (`area 0`) or a
          // dotted-quad (`area 0.0.0.1`). Both normalize to a 32-bit
          // area ID at the callback boundary.
          key "area-id";
          leaf area-id {
            ext:help "OSPF area identifier";
            type union {
              type uint32;
              type inet:ipv4-address;
            }
          }
          // RFC 2328 §3.6 / RFC 3101 §2: per-area type. `normal`
          // (default) carries the full LSDB; `stub` drops Type-5
          // AS-External; `nssa` drops Type-5 but accepts Type-7
          // (NSSA-AS-External). The N-bit (NSSA) and E-bit
          // (External) in Hello/DBD options follow this knob and a
          // mismatch with a neighbor causes Hello rejection per
          // RFC 3101 §2.5 / RFC 2328 §10.5.
          leaf area-type {
            ext:help "OSPF area type (normal/stub/nssa)";
            type enumeration {
              enum normal;
              enum stub;
              enum nssa;
            }
            default normal;
          }
          // Totally-stubby / totally-NSSA: also drop Type-3 Summary
          // entering this area. Only meaningful when area-type is
          // `stub` or `nssa`.
          leaf no-summary {
            ext:help "Block Type-3 summaries (totally stub/NSSA)";
            type boolean;
            default false;
          }
          // NSSA ABR originates a default Type-7 LSA into the area
          // (RFC 3101 §2.3). Ignored unless area-type is `nssa`.
          leaf nssa-default-originate {
            ext:help "Originate default Type-7 into the NSSA";
            type boolean;
            default false;
          }
          // RFC 3101 §2.6: when translating Type-7 to Type-5, zero
          // the forwarding address. Ignored unless area-type is
          // `nssa`.
          leaf nssa-suppress-fa {
            ext:help "Zero forwarding address in Type-7 to Type-5";
            type boolean;
            default false;
          }
          // RFC 3101 §2.2 translator-role for this NSSA ABR.
          // `candidate` (default) participates in Nt-bit election;
          // `always` translates unconditionally; `never` disables.
          // Ignored unless area-type is `nssa`.
          leaf nssa-translator-role {
            ext:help "NSSA Type-7 to Type-5 translator role";
            type enumeration {
              enum candidate;
              enum always;
              enum never;
            }
            default candidate;
          }
          // Per-NSSA-area redistribute knobs. Type-7 LSAs are
          // area-scoped, so the source proto is selected per area
          // (an operator may inject `connected` into one NSSA and
          // not another). Each sibling container is a presence node
          // — its existence enables redistribution of that source.
          // Ignored unless area-type is `nssa`. The metric and
          // metric-type leaves are consumer-side overrides: metric
          // defaults to 20 (matching FRR), metric-type defaults to
          // 2 (E2). Type-1 (E1) lifts the SPF cost to the originator
          // and adds the LSA metric; Type-2 uses LSA metric alone.
          container redistribute {
            ext:help "Redistribute into this NSSA area (Type-7)";
            container connected {
              ext:help "Redistribute connected routes";
              presence "Redistribute connected routes into Type-7";
              leaf metric {
                ext:help "Metric for redistributed routes";
                type uint32 {
                  range "0..16777214";
                }
                default 20;
              }
              leaf metric-type {
                ext:help "OSPF external metric type (1 or 2)";
                type enumeration {
                  enum type-1;
                  enum type-2;
                }
                default type-2;
              }
            }
          }
          // RFC 2328 §12.4.3 address ranges: at an ABR, intra-area
          // routes of THIS area that fall inside a range are not
          // advertised individually into the other areas — one
          // aggregate is advertised instead, at the largest component
          // metric (or the configured `cost`). `not-advertise`
          // suppresses the aggregate too, hiding the whole range.
          // Ranges never apply to routes re-advertised from other
          // areas.
          list range {
            ext:help "Area address range for aggregation";
            key "prefix";
            leaf prefix {
              ext:help "Aggregate prefix (A.B.C.D/len)";
              type inet:ipv4-prefix;
            }
            leaf not-advertise {
              ext:help "Suppress the aggregate and hide the range";
              type boolean;
              default false;
            }
            leaf cost {
              ext:help "Metric advertised for the aggregate";
              type uint32 {
                range "0..16777214";
              }
            }
          }
          list virtual-link {
            ext:help "Virtual link through this (transit) area to a remote ABR";
            // RFC 2328 §15: a logical backbone point-to-point link to
            // the ABR `router-id`, transiting THIS area. Comes up when
            // the transit-area SPF finds the peer reachable; cost and
            // endpoints are derived from that SPF. The list-key area
            // must be a non-backbone, non-stub area.
            key "router-id";
            leaf router-id {
              ext:help "Remote ABR router-id of the virtual link";
              type inet:ipv4-address;
            }
            leaf hello-interval {
              ext:help "Hello interval in seconds";
              type uint16 {
                range "1..65535";
              }
              units "seconds";
              default 10;
            }
            leaf dead-interval {
              ext:help "Dead (router) interval in seconds";
              type uint32 {
                range "1..4294967295";
              }
              units "seconds";
              default 40;
            }
            leaf retransmit-interval {
              ext:help "LSA retransmit interval in seconds";
              type uint16 {
                range "1..65535";
              }
              units "seconds";
              default 5;
            }
          }
          list interface {
            ext:help "OSPF interface";
            key "if-name";
            leaf if-name {
              ext:help "Interface name";
              ext:dynamic "rib:interface";
              type string;
            }
            leaf enabled {
              ext:help "Enable OSPF on this interface";
              type boolean;
            }
            leaf network-type {
              ext:help "OSPF network type (broadcast/p2p)";
              type enumeration {
                enum broadcast;
                enum point-to-point;
              }
            }
            leaf priority {
              ext:help "Router priority for DR election";
              type uint8;
            }
            leaf cost {
              ext:help "Interface output cost (SPF metric)";
              // RFC 2328 §C.3 interface output cost (Router-LSA link
              // metric / SPF edge weight). 16-bit; default 10.
              type uint16;
            }
            leaf hello-interval {
              ext:help "Hello interval in seconds";
              type uint16;
            }
            leaf dead-interval {
              ext:help "Dead (router) interval in seconds";
              type uint32;
            }
            leaf retransmit-interval {
              ext:help "LSA retransmit interval in seconds";
              type uint16;
            }
            leaf mtu-ignore {
              ext:help "Ignore MTU mismatch in DBD packets";
              type boolean;
            }
            // Passive interface: its prefixes keep advertising into
            // the area (Router-LSA stub / Intra-Area-Prefix-LSA) but
            // no Hello is sent or accepted, so no adjacency forms.
            // Loopbacks are implicitly passive even when unset.
            leaf passive {
              ext:help "Advertise but form no adjacency (passive)";
              type boolean;
              default false;
            }
            container prefix-sid {
              ext:help "Segment Routing Prefix-SID for this interface";
              leaf index {
                ext:help "Prefix-SID index into the SRGB";
                type uint32;
              }
              leaf absolute {
                ext:help "Absolute Prefix-SID label value";
                type uint32;
              }
            }
            list flex-algo-prefix-sid {
              ext:help "Per-flex-algo Prefix-SID for this interface";
              // Per-Flexible-Algorithm Prefix-SID for this interface's
              // prefix (RFC 9350 §7). Emitted as an extra Prefix-SID
              // sub-TLV (Algorithm = the keyed algo) in the
              // Extended-Prefix Opaque LSA, alongside the algo-0
              // `prefix-sid` above.
              key "algo";
              leaf algo {
                ext:help "Flex-Algorithm identifier (128-255)";
                type uint8 { range "128..255"; }
              }
              leaf index {
                ext:help "Prefix-SID index into the SRGB";
                type uint32;
              }
              leaf absolute {
                ext:help "Absolute Prefix-SID label value";
                type uint32;
              }
            }
            container adjacency-sid {
              ext:help "Segment Routing Adjacency-SID for this link";
              // Per-link Adjacency-SID (RFC 8665 §6). Originated in
              // the Extended-Link Opaque LSA (type 10 / opaque-type 8)
              // as an AdjSid sub-TLV. Either form is allowed; the
              // origination side picks the wire encoding from whichever
              // leaf is set.
              leaf index {
                ext:help "Adjacency-SID index value";
                type uint32;
              }
              leaf absolute {
                ext:help "Absolute Adjacency-SID label value";
                type uint32;
              }
            }
            leaf-list affinity {
              ext:help "Affinity (admin-group) names on this link";
              // Names of /affinity-map entries this link carries.
              // Advertised as an Extended Admin Group bitmap inside the
              // ASLA sub-TLV (RFC 9492) and tested against each FAD's
              // include/exclude constraints at flex-algo SPF time.
              type string;
            }
            container te-metric {
              ext:help "Static TE link metrics (RFC 7471) for this interface";
              description
                "Per-interface traffic-engineering link metrics advertised
                 as RFC 7471 link-attribute sub-TLVs carried in this link's
                 ASLA sub-TLV (RFC 9492) on the Extended-Link Opaque LSA —
                 the same place flex-algo affinity is advertised, and what
                 Flex-Algorithm metric-type 1 consumes. Segment Routing
                 is not required: it gates the Adj-SID contributions to
                 that LSA, not the LSA itself. Static configuration and
                 STAMP measurement populate the same fields; a static
                 leaf, when set, wins per field. All delay values are in
                 microseconds.";

              leaf unidirectional-delay {
                ext:help "Average unidirectional link delay (us)";
                type uint32 {
                  range "0..16777215";
                }
                units "microseconds";
                description
                  "Average unidirectional link delay (RFC 7471 §4.1,
                   sub-TLV 27).";
              }
              leaf min-delay {
                ext:help "Minimum unidirectional link delay (us)";
                type uint32 {
                  range "0..16777215";
                }
                units "microseconds";
                description
                  "Minimum unidirectional link delay (RFC 7471 §4.2,
                   sub-TLV 28). Advertised with max-delay; the Min/Max
                   sub-TLV is emitted only when both are set.";
              }
              leaf max-delay {
                ext:help "Maximum unidirectional link delay (us)";
                type uint32 {
                  range "0..16777215";
                }
                units "microseconds";
                description
                  "Maximum unidirectional link delay (RFC 7471 §4.2,
                   sub-TLV 28).";
              }
              leaf delay-variation {
                ext:help "Unidirectional delay variation / jitter (us)";
                type uint32 {
                  range "0..16777215";
                }
                units "microseconds";
                description
                  "Unidirectional delay variation / jitter (RFC 7471
                   §4.3, sub-TLV 29).";
              }
              leaf loss {
                ext:help "Unidirectional link loss ratio";
                type uint32 {
                  range "0..16777214";
                }
                description
                  "Unidirectional link loss (RFC 7471 §4.4, sub-TLV 30),
                   encoded in units of 0.000003 %; the maximum 16777214
                   (0xFFFFFE) is ~50.33 %.";
              }
              container measurement {
                ext:help "Measure this link's delay and loss dynamically (STAMP, RFC 8762)";
                description
                  "Active performance measurement of this link. When
                   enabled, a STAMP Session-Sender (RFC 8762,
                   unauthenticated) probes the P2P neighbor once the
                   adjacency reaches Full; the damped min/max/avg delay
                   and delay variation populate the same te-metric
                   fields as static configuration (a static leaf, when
                   set, overrides the measured value per field). The
                   probes are answered by the neighbor's implicit
                   Session-Reflector, so measurement must be enabled on
                   both ends of the link.";
                leaf enabled {
                  ext:help "Activate measurement on this interface";
                  type boolean;
                  description "Activate measurement on this interface.";
                }
                leaf interval {
                  ext:help "Probe transmit interval in milliseconds";
                  type uint32 {
                    range "100..60000";
                  }
                  units "milliseconds";
                  description "Probe transmit interval. Default 1000 ms.";
                }
                leaf damping-period {
                  ext:help "Minimum spacing between IGP exports (s)";
                  type uint32 {
                    range "1..3600";
                  }
                  units "seconds";
                  description
                    "Minimum spacing between exports to the IGP; each
                     period's samples form the advertised min/max/avg
                     window. Default 30 s.";
                }
                leaf anomaly-threshold {
                  ext:help "Average delay at/above which the Anomalous bit is set (us)";
                  type uint32 {
                    range "0..16777215";
                  }
                  units "microseconds";
                  description
                    "Upper bound for the measured average one-way delay. At or
                     above it, the Anomalous (A) bit is set on the delay
                     sub-TLVs this link advertises (RFC 7471 §4.1 and §4.2), telling
                     receivers the link has degraded past what the operator
                     accepts. Only measured values carry the bit: a delay
                     pinned by the sibling static leaves is always advertised
                     with it clear. Unset disables anomaly detection.";
                }
                leaf reuse-threshold {
                  ext:help "Average delay below which the Anomalous bit clears (us)";
                  type uint32 {
                    range "0..16777215";
                  }
                  units "microseconds";
                  description
                    "Lower bound at which a set Anomalous bit clears again.
                     Between this and anomaly-threshold the bit holds its
                     current state, so a link resting on the bound does not
                     re-originate every export period. Values above
                     anomaly-threshold are clamped to it. Unset means no
                     hysteresis band: anomaly-threshold both sets and clears.";
                }
                leaf reflector {
                  ext:help "How this router reflects the peer's probes (default stateless)";
                  type enumeration {
                    enum stateless;
                    enum stateful;
                  }
                  description
                    "stateless (the default, RFC 8762 section 4.3): replies copy the
                     sender's sequence number. stateful: replies carry this router's own
                     per-peer sequence counter, which lets a peer that declares
                     'loss peer-reflector stateful' tell forward loss from reverse. On if
                     any IGP measuring this link sets it.";
                }
                container loss {
                  ext:help "Measured link loss (RFC 8570 / RFC 7471 section 4.4)";
                  description
                    "Round-trip probe loss, measured on the same STAMP session
                     and advertised as the unidirectional link-loss sub-TLV. On
                     by default wherever measurement is enabled. Loss runs on
                     its own 30 s bucket clock, independent of damping-period. A
                     static te-metric loss, when set, overrides the measured
                     value.";
                  leaf enabled {
                    ext:help "Advertise measured loss (default true)";
                    type boolean;
                    description "Advertise measured loss. Default true.";
                  }
                  leaf interval {
                    ext:help "Loss averaging and advertisement interval (s, multiple of 30)";
                    type uint32 {
                      range "30..3600";
                    }
                    units "seconds";
                    description
                      "Loss is averaged over the last interval, and re-advertised
                       at most once per interval. Must be a multiple of 30.
                       Default 120 s.";
                  }
                  leaf threshold {
                    ext:help "Re-advertise on a change of this percent of the advertised value";
                    type uint32 {
                      range "0..100";
                    }
                    units "percent";
                    description
                      "A periodic re-advertisement needs a change of at least this
                       percentage of the advertised value, and at least
                       minimum-change. Default 10.";
                  }
                  leaf minimum-change {
                    ext:help "Re-advertise only on a change of at least this many percentage points";
                    type decimal64 {
                      fraction-digits 6;
                    }
                    units "percent";
                    description
                      "The smallest absolute change, in percentage points, that is
                       re-advertised. It also governs changes to and from zero.
                       At the default probe rate one lost probe is 0.83 %, so a
                       smaller value lets single-probe noise re-flood. Default 1.0.";
                  }
                  leaf accelerated-threshold {
                    ext:help "Advertise at once when the latest 30 s differs by this many points";
                    type decimal64 {
                      fraction-digits 6;
                    }
                    units "percent";
                    description
                      "When the latest 30 s bucket alone differs from the
                       advertised value by at least this many percentage points,
                       advertise that value at once instead of waiting for the
                       interval. Unset (the default) disables acceleration.";
                  }
                  leaf integrity {
                    ext:help "Minimum percent of expected probes for a window to be trusted";
                    type uint32 {
                      range "1..100";
                    }
                    units "percent";
                    description
                      "A loss window is advertised only when at least this
                       percentage of the probes the probe interval should have
                       produced actually settled. Default 90.";
                  }
                  leaf anomaly-threshold {
                    ext:help "Set the Anomalous bit at or above this loss (percent)";
                    type decimal64 {
                      fraction-digits 6;
                    }
                    units "percent";
                    description
                      "Loss, in percent, at or above which the link-loss sub-TLV's
                       Anomalous (A) bit is set, evaluated on the value it is advertised
                       with (RFC 8570 / RFC 7471 section 4.4). Unset (the default) never
                       sets the bit.";
                  }
                  leaf reuse-threshold {
                    ext:help "Clear the Anomalous bit after a loss interval below this loss (percent)";
                    type decimal64 {
                      fraction-digits 6;
                    }
                    units "percent";
                    description
                      "Loss, in percent, below which the Anomalous bit clears once the
                       loss has stayed below it for a whole loss interval. Defaults to,
                       and is capped at, anomaly-threshold.";
                  }
                  leaf peer-reflector {
                    ext:help "How the peer reflects this router's probes (default stateless)";
                    type enumeration {
                      enum stateless;
                      enum stateful;
                    }
                    description
                      "Declares the peer's reflector mode; it cannot be detected.
                       stateless (the default): the advertised loss is round-trip, an upper
                       bound on forward loss. stateful: the peer reflects with its own
                       sequence counter (a zebra-rs peer with 'measurement reflector
                       stateful', a Juniper peer with stateful-sequence), losses are split
                       by direction, and forward loss is advertised. Declaring a stateless
                       peer stateful makes every loss read as reverse.";
                  }
                }
              }
            }
          }
        }
        container segment-routing {
          ext:help "Segment Routing configuration";
          // Mirrors `router isis / segment-routing` (config.yang L516).
          // OSPFv2 carries SR over MPLS only — there is no OSPFv2 SRv6
          // (OSPFv2 is IPv4-only on the wire); the SRv6 sibling lives
          // under `router ospfv3 / segment-routing` instead.
          container mpls {
            ext:help "Segment Routing over MPLS dataplane";
            presence "Enable Segment Routing over MPLS dataplane";
          }
        }

        list flex-algo {
          ext:help "Flexible Algorithm (RFC 9350) definition";
          // OSPFv2 Flexible Algorithm (RFC 9350 §6) definition. Mirrors
          // `router isis / flex-algo`; keyed by the on-the-wire numeric
          // identifier (128..255). `advertise-definition true` causes
          // this router to originate the FAD TLV in its Router
          // Information Opaque LSA (RFC 9350 §6.1, RI TLV 16); without
          // it the router participates using a FAD learned from another
          // node. At least one (preferably two) routers per area MUST
          // advertise the definition.
          key "algo";
          leaf algo {
            ext:help "Flex-Algorithm identifier (128..255)";
            type uint8 { range "128..255"; }
            description
              "Flex-Algorithm identifier (RFC 9350 §4). 0..127 are
               reserved by IANA; 128..255 are user-defined.";
          }

          leaf advertise-definition {
            ext:help "Originate the FAD TLV for this algorithm";
            type boolean;
            default false;
            description
              "When true, originate the FAD TLV for this algorithm in
               the Router Information Opaque LSA. If no router in the
               area advertises the FAD, every participant fails to
               compute paths.";
          }

          leaf metric-type {
            ext:help "FAD metric-type (igp, delay, te)";
            type enumeration {
              enum igp;                   // FAD Metric-Type 0
              enum min-unidir-link-delay; // FAD Metric-Type 1 (RFC 8570)
              enum te-default;            // FAD Metric-Type 2 (RFC 5305)
            }
            default igp;
          }

          leaf priority {
            ext:help "FAD advertisement priority (higher wins)";
            // FAD Priority (RFC 9350 §6.5). Tie-breaker when more than
            // one router originates a FAD for the same algo; higher
            // priority wins.
            type uint8;
            default 128;
          }

          leaf prefix-metric {
            ext:help "Include Flex-Algo prefix metric (M-flag)";
            // M-flag in the FAD Flags sub-TLV (RFC 9350 §6.4). When set,
            // the computed path metric to a prefix includes the
            // advertised Flexible Algorithm Prefix Metric.
            type boolean;
            default false;
          }

          container dataplane {
            ext:help "Per-algorithm dataplane selection";
            // Per-algorithm dataplane participation. OSPFv2 carries SR
            // over MPLS only (no OSPFv2 SRv6); the `ip` flag selects
            // plain IP forwarding for the algo's computed paths.
            leaf sr-mpls {
              ext:help "Use SR-MPLS forwarding for this algo";
              type boolean; default false; }
            leaf ip      {
              ext:help "Use plain IP forwarding for this algo";
              type boolean; default false; }
          }

          container affinity {
            ext:help "Flex-Algo admin-group (affinity) constraints";
            // FAD Exclude / Include-Any / Include-All Admin Group
            // sub-TLVs (RFC 9350 §6.2-6.4). Each leaf-list value is a
            // name from the global /affinity-map table.
            leaf-list include-any {
              ext:help "Admin-groups a link must include any of";
              type string; }
            leaf-list include-all {
              ext:help "Admin-groups a link must include all of";
              type string; }
            leaf-list exclude-any {
              ext:help "Admin-groups that exclude a link";
              type string; }
          }

          leaf-list srlg-exclude {
            ext:help "SRLG groups excluded from this algo";
            // FAD Exclude SRLG sub-TLV (RFC 9350 §6.5). Each entry
            // references a /srlg/group name.
            type string;
          }

          container fast-reroute {
            ext:help "Per-algo fast-reroute";
            // Per-algorithm fast-reroute OPT-OUT; same model and rationale
            // as `router isis / flex-algo / fast-reroute`. TI-LFA
            // enablement is instance-level
            // (/router/ospf/fast-reroute/ti-lfa) and every algorithm this
            // router participates in inherits it. The per-algorithm
            // computation itself is still deferred for OSPFv2 — the leaf
            // is accepted and stored so the schema stays uniform across
            // IS-IS / OSPFv2 / OSPFv3, but nothing consumes it yet.
            leaf disable {
              ext:help "Disable fast-reroute for this flex-algo";
              type empty;
              description
                "Suppress TI-LFA repair computation and installation for
                 this Flex-Algorithm only; algorithm 0 and every other
                 algorithm keep whatever /router/ospf/fast-reroute/ti-lfa
                 configures.";
            }
          }
        }

        container fast-reroute {
          ext:help "IP fast-reroute (LFA) mechanisms";
          // OSPFv2 fast-reroute mechanisms (RFC 7490 LFA family).
          // Empty container is a no-op; the per-mechanism child
          // presence containers turn features on. Shape mirrors
          // `router isis / fast-reroute`.
          container ti-lfa {
            ext:help "Topology-Independent LFA (TI-LFA)";
            // Topology-Independent Loop-Free Alternate (TI-LFA,
            // RFC 9855). Computes a post-convergence repair path
            // expressed as SR-MPLS labels, so segment-routing/mpls
            // must also be enabled for the repair to install in the
            // dataplane.
            presence "Enable Topology-Independent LFA (TI-LFA)";

            container compute-mode {
              ext:help "How the TI-LFA computation is scheduled";
              // Execution scheduling for the per-destination TI-LFA
              // computation; same modes and semantics as
              // `router isis fast-reroute ti-lfa compute-mode` (see
              // docs/design/isis-tilfa-parallel-spf.md, §13 for the
              // OSPF specifics). One keyword per mode under a `choice`;
              // the shard count nests under `sharding`. The default
              // mode (serial) is applied by the Rust handler.
              choice mode {
                case serial {
                  leaf serial {
                    ext:help "Run on the SPF worker thread";
                    type empty;
                  }
                }
                case conservative {
                  leaf conservative {
                    ext:help "Fan out one task per destination";
                    type empty;
                  }
                }
                case aggressive {
                  leaf aggressive {
                    ext:help "Also share the PC-path SPF per protected node";
                    type empty;
                  }
                }
                case sharding {
                  container sharding {
                    ext:help "Aggressive work split into parallel shards";
                    presence "Shard the aggressive computation (default 8 shards)";
                    // Hard upper bound on TI-LFA parallelism, consulted
                    // only in this mode. Bare `sharding` uses 8
                    // (applied by the handler).
                    leaf shards {
                      ext:help "Max parallel TI-LFA shards";
                      type uint16 {
                        range "1..256";
                      }
                      default "8";
                    }
                  }
                }
              }
            }
          }
          container backup-as-primary {
            ext:help "Install TI-LFA backup as primary nexthop";
            // Swap the metric-sort offset between the SPF primary
            // nexthop and the TI-LFA repair: the repair installs at
            // route.metric (sorted first) and the primary installs at
            // route.metric + BACKUP_METRIC_OFFSET. Lets operators pin
            // traffic onto the TI-LFA path for protection testing
            // without rewiring the topology.
            presence "Install TI-LFA backup as the primary nexthop";
          }
        }

        container graceful-restart {
          ext:help "Graceful restart (RFC 3623) helper config";
          // RFC 3623 helper-side configuration. zebra-rs is
          // helper-only today (Phase 5 restarter mode is deferred).
          // Defaults match the IETF YANG model
          // (ietf-ospf@2022-10-19.yang) and FRR's helper defaults.
          leaf helper-enabled {
            ext:help "Accept Grace LSAs and act as helper";
            type boolean;
            default true;
            description
              "Accept Grace LSAs and enter helper mode. When false,
               the Grace-LSA receive path drops every Grace LSA
               regardless of grace-period / strict-lsa-checking
               state.";
          }
          leaf max-grace-period {
            ext:help "Max grace period honoured, seconds";
            type uint32;
            units "seconds";
            default 1800;
            description
              "Upper bound on the grace period we will honour. A
               Grace LSA requesting more than this value is
               rejected (RFC 3623 §3.1 leaves the bound to the
               helper's policy).";
          }
          leaf helper-strict-lsa-checking {
            ext:help "Exit helper on topology change";
            type boolean;
            default true;
            description
              "When true, any topology-affecting LSA from a
               non-restarter that floods through the helper's area
               exits helper immediately (RFC 3623 §3.2). When
               false, only the restarter's own LSAs trigger exit —
               useful when transient changes elsewhere shouldn't
               cut the restart short.";
          }
          leaf drain-time-ms {
            ext:help "Grace-LSA drain window before exit, ms";
            type uint32 {
              range "50..2000";
            }
            units "milliseconds";
            default 200;
            description
              "Window between writing the restart checkpoint and
               exiting the process during `clear ip ospf
               graceful-restart commit`. Picked so the Grace LSAs
               reach the wire before the raw socket closes; 200ms
               is the high end of imperceptible on LAN, absorbs
               tunnel RTTs up to ~100ms.";
          }
        }

        leaf min-ls-interval {
          ext:help "Minimum interval between re-originations of a self-LSA (MinLSInterval)";
          // RFC 2328 §12.4 MinLSInterval (FRR `timers throttle lsa
          // all`): the minimum spacing between two originations of the
          // same self-LSA. A re-origination requested sooner is
          // deferred to the interval boundary, coalescing a burst of
          // topology changes into one Router-LSA / Network-LSA update.
          // Default 5000ms per the RFC.
          type uint32 {
            range "0..5000";
          }
          units "milliseconds";
          default 5000;
        }

        leaf min-ls-arrival {
          ext:help "Minimum interval between accepted flooded copies of an LSA (MinLSArrival)";
          // RFC 2328 §13 MinLSArrival (FRR `timers lsa min-arrival`):
          // the receive-side rate limit. A flooded instance arriving
          // less than this after the last accepted copy is discarded
          // without acknowledgement. Default 1000ms per the RFC.
          type uint32 {
            range "0..600000";
          }
          units "milliseconds";
          default 1000;
        }

        container max-metric {
          ext:help "Advertise own Router-LSA with maximum metric (RFC 6987 stub router)";
          container router-lsa {
            ext:help "Advertise transit links at MaxLinkMetric (0xFFFF)";
            // RFC 6987 stub router (FRR `max-metric router-lsa ...`):
            // while active, every transit link (P2p / Transit /
            // VirtualLink) in our Router-LSAs carries MaxLinkMetric so
            // neighbors stop routing transit traffic through us; stub
            // links keep their configured cost, so our own prefixes
            // stay reachable. `administrative` holds the state
            // indefinitely (maintenance); `on-startup` holds it for N
            // seconds after the config applies (boot grace, e.g. to
            // let BGP converge before drawing transit traffic).
            presence "RFC 6987 stub-router configuration";
            leaf administrative {
              ext:help "Indefinite (administrative) stub router";
              type boolean;
              default false;
            }
            leaf on-startup {
              ext:help "Stub-router window after startup, seconds";
              type uint32 {
                range "5..86400";
              }
              units "seconds";
            }
          }
        }

        container spf-interval {
          ext:help "SPF calculation throttle timers";
          // Adaptive IOS-XR-style exponential hold-down, replacing the
          // old fixed 1-second coalescing timer. The first SPF after a
          // quiet period waits `initial-wait`; sustained churn backs
          // off `secondary-wait` then doubles up to `maximum-wait`.
          // Per-area state, so a churning area backs off without
          // slowing a stable one. Defaults 50/200/5000ms match
          // zebra-rs IS-IS `spf-interval`.
          leaf initial-wait {
            ext:help "Delay before the first SPF run, ms";
            type uint32 {
              range "1..120000";
            }
            units "milliseconds";
            default 50;
            description
              "Delay from the first topology change after a quiet
               period to the first SPF run.";
          }
          leaf secondary-wait {
            ext:help "Hold-down between SPF runs in a burst, ms";
            type uint32 {
              range "1..120000";
            }
            units "milliseconds";
            default 200;
            description
              "Hold-down before the next SPF while a burst is in
               progress; doubles each successive run up to
               maximum-wait.";
          }
          leaf maximum-wait {
            ext:help "Maximum SPF hold-down, ms";
            type uint32 {
              range "1..120000";
            }
            units "milliseconds";
            default 5000;
            description
              "Upper bound on the SPF hold-down. A quiet period
               longer than twice this value resets the backoff to
               initial-wait.";
          }
        }

        list vrf {
          ext:help "Per-VRF OSPFv2 instance";
          // Per-VRF OSPFv2 instance. The default `router ospf` task
          // forwards each `vrf <name> ...` line (with the `vrf <name>`
          // prefix stripped) to a full per-VRF OSPFv2 instance whose
          // computed routes install into the VRF's routing table. The
          // `vrf` key is a plain string (staging-friendly, like
          // `router static`'s per-VRF list) so the VRF need not yet
          // exist at the top-level `vrf` list when parsed. The exposed
          // subset tracks the default instance's per-interface knobs
          // (enabled / network-type / priority / timers) plus per-area
          // NSSA `redistribute connected`; more leaves land as the
          // per-VRF surface widens.
          key "name";
          leaf name {
            ext:help "VRF name";
            ext:dynamic "rib:vrf";
            type string;
          }
          leaf router-id {
            ext:help "OSPF router identifier for this VRF";
            type inet:ipv4-address;
          }
          // Instance-level redistribution into Type-5 AS-External LSAs,
          // forwarded to the per-VRF instance (prefix stripped) and hitting
          // the same callbacks as the default instance. `redistribute bgp`
          // lets a PE inject VPNv4 routes it imported into this VRF into the
          // CE-facing OSPF (the L3VPN PE-CE down direction).
          container redistribute {
            ext:help "Redistribute routes into this VRF's OSPF";
            container connected {
              ext:help "Redistribute connected routes (Type-5)";
              presence "Redistribute connected routes as Type-5 AS-External LSAs";
              leaf metric {
                ext:help "External metric for redistributed routes";
                type uint32 {
                  range "0..16777214";
                }
                default 20;
              }
              leaf metric-type {
                ext:help "External metric type (E1 or E2)";
                type enumeration {
                  enum type-1;
                  enum type-2;
                }
                default type-2;
              }
            }
            container bgp {
              ext:help "Redistribute BGP routes (Type-5)";
              presence "Redistribute BGP routes as Type-5 AS-External LSAs";
              leaf metric {
                ext:help "External metric for redistributed routes";
                type uint32 {
                  range "0..16777214";
                }
                default 20;
              }
              leaf metric-type {
                ext:help "External metric type (E1 or E2)";
                type enumeration {
                  enum type-1;
                  enum type-2;
                }
                default type-2;
              }
            }
          }
          list area {
            ext:help "OSPF area within this VRF";
            key "area-id";
            leaf area-id {
              ext:help "Area identifier (decimal or A.B.C.D)";
              type union {
                type uint32;
                type inet:ipv4-address;
              }
            }
            // Per-NSSA-area redistribute into Type-7 (mirrors the
            // default instance). Forwarded paths
            // `/router/ospf/area/redistribute/connected[/metric|
            // /metric-type]` match the existing v2 callbacks.
            container redistribute {
              ext:help "Per-area NSSA redistribution (Type-7)";
              container connected {
                ext:help "Redistribute connected routes into Type-7";
                presence "Redistribute connected routes into Type-7";
                leaf metric {
                  ext:help "External metric for redistributed routes";
                  type uint32 {
                    range "0..16777214";
                  }
                  default 20;
                }
                leaf metric-type {
                  ext:help "External metric type (E1 or E2)";
                  type enumeration {
                    enum type-1;
                    enum type-2;
                  }
                  default type-2;
                }
              }
            }
            list interface {
              ext:help "Per-interface OSPF configuration";
              key "if-name";
              leaf if-name {
                ext:help "Interface name";
                ext:dynamic "rib:interface";
                type string;
              }
              leaf enabled {
                ext:help "Enable OSPF on this interface";
                type boolean;
              }
              leaf network-type {
                ext:help "OSPF network type (broadcast or p2p)";
                type enumeration {
                  enum broadcast;
                  enum point-to-point;
                }
              }
              leaf priority {
                ext:help "DR election priority";
                type uint8;
              }
              leaf hello-interval {
                ext:help "Hello packet interval, seconds";
                type uint16;
              }
              leaf dead-interval {
                ext:help "Neighbor dead interval, seconds";
                type uint32;
              }
              leaf retransmit-interval {
                ext:help "LSA retransmit interval, seconds";
                type uint16;
              }
              leaf mtu-ignore {
                ext:help "Ignore MTU mismatch in DBD packets";
                type boolean;
              }
            }
          }
        }
      }
      container ospfv3 {
        ext:help "OSPFv3 (IPv6) configuration";
        // OSPFv3 (RFC 5340). Shape mirrors `container ospf` so a
        // v3 config differs from v2 only in the top-level keyword.
        // Per-interface knobs (`priority`, `hello-interval`,
        // `dead-interval`, `retransmit-interval`, `mtu-ignore`,
        // `network-type`) share semantics with their v2
        // counterparts; the v3 callbacks live in `config_v3.rs`.
        presence "Enables configuration of OSPFv3";
        leaf router-id {
          ext:help "OSPFv3 router identifier";
          type inet:ipv4-address;
        }
        // Instance-level redistribution into AS-External (Type-5) LSAs.
        // Instance-level redistribute into AS-External (Type-5) LSAs,
        // flooded AS-wide into all normal areas. Sources mirror the v2
        // sibling (connected / static / kernel / isis / bgp);
        // `redistribute bgp` additionally serves the SRv6 L3VPN PE-CE
        // down direction: a PE injects the VPNv6 routes it imported
        // into a VRF into the CE-facing OSPFv3. Per-area NSSA
        // redistribution is under list area / redistribute.
        container redistribute {
          ext:help "Redistribute routes into OSPFv3";
          container connected {
            ext:help "Redistribute connected routes (Type-5)";
            presence "Redistribute connected routes as AS-External (Type-5) LSAs";
            leaf metric {
              ext:help "External metric for redistributed routes";
              type uint32 {
                range "0..16777214";
              }
              default 20;
            }
            leaf metric-type {
              ext:help "External metric type (E1 or E2)";
              type enumeration {
                enum type-1;
                enum type-2;
              }
              default type-2;
            }
            leaf route-map {
              ext:help "Filter/modify redistributed routes via a named policy-list";
              type string;
            }
          }
          container static {
            ext:help "Redistribute static routes (Type-5)";
            presence "Redistribute static routes as AS-External (Type-5) LSAs";
            leaf metric {
              ext:help "External metric for redistributed routes";
              type uint32 {
                range "0..16777214";
              }
              default 20;
            }
            leaf metric-type {
              ext:help "External metric type (E1 or E2)";
              type enumeration {
                enum type-1;
                enum type-2;
              }
              default type-2;
            }
            leaf route-map {
              ext:help "Filter/modify redistributed routes via a named policy-list";
              type string;
            }
          }
          container kernel {
            ext:help "Redistribute kernel routes (Type-5)";
            presence "Redistribute kernel routes as AS-External (Type-5) LSAs";
            leaf metric {
              ext:help "External metric for redistributed routes";
              type uint32 {
                range "0..16777214";
              }
              default 20;
            }
            leaf metric-type {
              ext:help "External metric type (E1 or E2)";
              type enumeration {
                enum type-1;
                enum type-2;
              }
              default type-2;
            }
            leaf route-map {
              ext:help "Filter/modify redistributed routes via a named policy-list";
              type string;
            }
          }
          container isis {
            ext:help "Redistribute IS-IS routes (Type-5)";
            presence "Redistribute IS-IS routes as AS-External (Type-5) LSAs";
            leaf metric {
              ext:help "External metric for redistributed routes";
              type uint32 {
                range "0..16777214";
              }
              default 20;
            }
            leaf metric-type {
              ext:help "External metric type (E1 or E2)";
              type enumeration {
                enum type-1;
                enum type-2;
              }
              default type-2;
            }
            leaf route-map {
              ext:help "Filter/modify redistributed routes via a named policy-list";
              type string;
            }
          }
          container bgp {
            ext:help "Redistribute BGP routes (Type-5)";
            presence "Redistribute BGP routes as AS-External (Type-5) LSAs";
            leaf metric {
              ext:help "External metric for redistributed routes";
              type uint32 {
                range "0..16777214";
              }
              default 20;
            }
            leaf metric-type {
              ext:help "External metric type (E1 or E2)";
              type enumeration {
                enum type-1;
                enum type-2;
              }
              default type-2;
            }
            leaf route-map {
              ext:help "Filter/modify redistributed routes via a named policy-list";
              type string;
            }
          }
        }
        // FRR-parity `default-information originate`: advertise a
        // Type-5 default route. Without `always` it is originated
        // only while a non-OSPF default route sits in the RIB
        // (tracked via the RIB default-route watch); `always`
        // originates unconditionally. Metric defaults to 10 (FRR
        // convention for the originated default; redistribute uses
        // 20), E2 semantics.
        container default-information {
          ext:help "Control default-route origination";
          container originate {
            ext:help "Originate a Type-5 default route";
            presence "Originate a Type-5 default route";
            leaf always {
              ext:help "Originate default even without a RIB default";
              type boolean;
              default false;
            }
            leaf metric {
              ext:help "Metric for the originated default route";
              type uint32 {
                range "0..16777214";
              }
              default 10;
            }
            leaf metric-type {
              ext:help "Default-route metric type (E1 or E2)";
              type enumeration {
                enum type-1;
                enum type-2;
              }
              default type-2;
            }
          }
        }
        // RFC 3623/5187 graceful-restart configuration — v3 sibling
        // of the v2 block. Helper knobs plus the restarter drain
        // window; the restart itself is operator-driven via
        // `clear ospfv3 graceful-restart begin|commit|abort`.
        container graceful-restart {
          ext:help "Graceful restart helper configuration";
          leaf helper-enabled {
            ext:help "Accept Grace LSAs and act as helper";
            type boolean;
            default true;
          }
          leaf max-grace-period {
            ext:help "Max grace period honoured, seconds";
            type uint32;
            units "seconds";
            default 1800;
          }
          leaf helper-strict-lsa-checking {
            ext:help "Exit helper on topology change";
            type boolean;
            default true;
          }
          leaf drain-time-ms {
            ext:help "Grace-LSA drain window before exit, ms";
            type uint32 {
              range "50..2000";
            }
            units "milliseconds";
            default 200;
          }
        }
        // MinLSInterval — v6 sibling of the v2 min-ls-interval leaf.
        leaf min-ls-interval {
          ext:help "Minimum interval between re-originations of a self-LSA (MinLSInterval)";
          type uint32 {
            range "0..5000";
          }
          units "milliseconds";
          default 5000;
        }
        container max-metric {
          ext:help "Advertise self as a stub router (RFC 5340 R-bit clear)";
          container router-lsa {
            ext:help "Clear the R/V6 option bits in own Router-LSAs";
            // v6 sibling of the v2 max-metric block, realized the
            // RFC 5340 way (ospf6d's `stub-router`): while active,
            // own Router-LSAs carry R=0/V6=0 so other routers
            // exclude this vertex from transit paths (§4.8.1) while
            // its own prefixes stay reachable.
            presence "RFC 5340 stub-router configuration";
            leaf administrative {
              ext:help "Indefinite (administrative) stub router";
              type boolean;
              default false;
            }
            leaf on-startup {
              ext:help "Stub-router window after startup, seconds";
              type uint32 {
                range "5..86400";
              }
              units "seconds";
            }
          }
        }

        // MinLSArrival — v6 sibling of the v2 min-ls-arrival leaf.
        leaf min-ls-arrival {
          ext:help "Minimum interval between accepted flooded copies of an LSA (MinLSArrival)";
          type uint32 {
            range "0..600000";
          }
          units "milliseconds";
          default 1000;
        }
        // Adaptive SPF throttle — v6 sibling of the v2 spf-interval
        // block. Same IOS-XR backoff and 50/200/5000ms defaults.
        container spf-interval {
          ext:help "SPF calculation throttle timers";
          leaf initial-wait {
            ext:help "Delay before the first SPF run, ms";
            type uint32 {
              range "1..120000";
            }
            units "milliseconds";
            default 50;
          }
          leaf secondary-wait {
            ext:help "Hold-down between SPF runs in a burst, ms";
            type uint32 {
              range "1..120000";
            }
            units "milliseconds";
            default 200;
          }
          leaf maximum-wait {
            ext:help "Maximum SPF hold-down, ms";
            type uint32 {
              range "1..120000";
            }
            units "milliseconds";
            default 5000;
          }
        }
        list area {
          ext:help "OSPFv3 area";
          key "area-id";
          leaf area-id {
            ext:help "Area identifier (decimal or A.B.C.D)";
            type union {
              type uint32;
              type inet:ipv4-address;
            }
          }
          // Per-area type. Same semantics as the v2 sibling above —
          // see that leaf's description. Phase 1 wires the option-bit
          // negotiation only; v3 Type-7 (0x2007) codec + handling
          // arrives in phases 5/6.
          leaf area-type {
            ext:help "Area type (normal, stub, or nssa)";
            type enumeration {
              enum normal;
              enum stub;
              enum nssa;
            }
            default normal;
          }
          leaf no-summary {
            ext:help "Totally-stubby: drop Type-3 summaries too";
            type boolean;
            default false;
          }
          leaf nssa-default-originate {
            ext:help "Originate a Type-7 default into NSSA";
            type boolean;
            default false;
          }
          leaf nssa-suppress-fa {
            ext:help "Zero the forwarding address in translation";
            type boolean;
            default false;
          }
          leaf nssa-translator-role {
            ext:help "Type-7-to-Type-5 translator role";
            type enumeration {
              enum candidate;
              enum always;
              enum never;
            }
            default candidate;
          }
          // Same shape as the v2 sibling above. Storage-only on v3
          // until phase 5/6 lights up Type-0x2007 origination — the
          // schema lives here today so v3 callers don't see a
          // schema drift between v2 and v3 NSSA config surfaces.
          container redistribute {
            ext:help "Per-area NSSA redistribution (Type-7)";
            container connected {
              ext:help "Redistribute connected routes into Type-7";
              presence "Redistribute connected routes into Type-7";
              leaf metric {
                ext:help "External metric for redistributed routes";
                type uint32 {
                  range "0..16777214";
                }
                default 20;
              }
              leaf metric-type {
                ext:help "External metric type (E1 or E2)";
                type enumeration {
                  enum type-1;
                  enum type-2;
                }
                default type-2;
              }
            }
          }
          // RFC 2328 §12.4.3 address ranges: at an ABR, intra-area
          // routes of THIS area that fall inside a range are not
          // advertised individually into the other areas — one
          // aggregate is advertised instead, at the largest component
          // metric (or the configured `cost`). `not-advertise`
          // suppresses the aggregate too, hiding the whole range.
          // Ranges never apply to routes re-advertised from other
          // areas.
          list range {
            ext:help "Area address range for summarization";
            key "prefix";
            leaf prefix {
              ext:help "IPv6 prefix to summarize";
              type inet:ipv6-prefix;
            }
            leaf not-advertise {
              ext:help "Suppress the aggregate and its components";
              type boolean;
              default false;
            }
            leaf cost {
              ext:help "Metric for the aggregated range";
              type uint32 {
                range "0..16777214";
              }
            }
          }
          list interface {
            ext:help "Per-interface OSPFv3 configuration";
            key "if-name";
            leaf if-name {
              ext:help "Interface name";
              ext:dynamic "rib:interface";
              type string;
            }
            leaf enabled {
              ext:help "Enable OSPFv3 on this interface";
              type boolean;
            }
            leaf network-type {
              ext:help "OSPFv3 network type (broadcast or p2p)";
              type enumeration {
                enum broadcast;
                enum point-to-point;
              }
            }
            leaf priority {
              ext:help "DR election priority";
              type uint8;
            }
            leaf cost {
              ext:help "Interface output cost (link metric)";
              // RFC 2328 §C.3 interface output cost, kept by RFC 5340:
              // the metric stamped on this link in the Router-LSA and
              // on its prefixes in the Intra-Area-Prefix-LSA (SPF edge
              // weight). 16-bit; default 10.
              type uint16;
            }
            leaf hello-interval {
              ext:help "Hello packet interval, seconds";
              type uint16;
            }
            leaf dead-interval {
              ext:help "Neighbor dead interval, seconds";
              type uint32;
            }
            leaf retransmit-interval {
              ext:help "LSA retransmit interval, seconds";
              type uint16;
            }
            leaf instance-id {
              ext:help "OSPFv3 Instance ID carried in packet headers (RFC 5340)";
              // RFC 5340 §A.3.1: separates multiple OSPFv3 instances
              // sharing one link. Both ends must match — a receiver
              // drops packets whose Instance ID differs from the
              // interface's (§8.2). Default 0.
              type uint8;
              default 0;
            }
            leaf mtu-ignore {
              ext:help "Ignore MTU mismatch in DBD packets";
              type boolean;
            }
            // Passive interface — same semantics as the v2 sibling.
            leaf passive {
              ext:help "Advertise prefix but form no adjacency";
              type boolean;
              default false;
            }
            container prefix-sid {
              ext:help "Prefix-SID for this interface prefix (algo 0)";
              leaf index {
                ext:help "Prefix-SID as an SRGB index";
                type uint32;
              }
              leaf absolute {
                ext:help "Prefix-SID as an absolute label value";
                type uint32;
              }
            }
            container adjacency-sid {
              ext:help "Per-link Adjacency-SID (SR-MPLS)";
              // Per-link Adjacency-SID. OSPFv3 SR-MPLS carries it in
              // the RFC 8666 Extended-Link LSA; storage-only here.
              // Either form is allowed; the origination side picks
              // the wire encoding from whichever leaf is set.
              leaf index {
                ext:help "Adjacency-SID as an SRGB index";
                type uint32;
              }
              leaf absolute {
                ext:help "Adjacency-SID as an absolute label value";
                type uint32;
              }
            }
            list flex-algo-prefix-sid {
              ext:help "Per-flex-algo Prefix-SID for this prefix";
              // Per-Flexible-Algorithm Prefix-SID for this interface's
              // prefix (RFC 9350 §7). Emitted as an extra Prefix-SID
              // sub-TLV (Algorithm = the keyed algo) in the
              // E-Intra-Area-Prefix-LSA, alongside the algo-0
              // `prefix-sid` above. Mirrors `router ospf` interface.
              key "algo";
              leaf algo {
                ext:help "Flex-Algorithm identifier (128..255)";
                type uint8 { range "128..255"; }
              }
              leaf index {
                ext:help "Prefix-SID as an SRGB index";
                type uint32;
              }
              leaf absolute {
                ext:help "Prefix-SID as an absolute label value";
                type uint32;
              }
            }
            container te-metric {
              ext:help "Static TE link metrics (RFC 7471) for this interface";
              description
                "Per-interface traffic-engineering link metrics advertised
                 as RFC 7471 link-attribute sub-TLVs carried in this link's
                 ASLA sub-TLV (RFC 9492) on the E-Router-LSA Router-Link TLV —
                 the same place flex-algo affinity is advertised, and what
                 Flex-Algorithm metric-type 1 consumes. OSPFv3 draws
                 these code points from the Extended-LSA sub-TLV registry
                 (13-16), not the OSPFv2 TE Opaque LSA one (27-30).
                 Segment Routing is not required: it gates the Adj-SID
                 and End.X contributions to the E-Router-LSA, not the
                 LSA itself. Static configuration and STAMP measurement
                 populate the same fields; a static leaf, when set, wins
                 per field. All delay values are in microseconds.";

              leaf unidirectional-delay {
                ext:help "Average unidirectional link delay (us)";
                type uint32 {
                  range "0..16777215";
                }
                units "microseconds";
                description
                  "Average unidirectional link delay (RFC 7471 §4.1,
                   sub-TLV 13).";
              }
              leaf min-delay {
                ext:help "Minimum unidirectional link delay (us)";
                type uint32 {
                  range "0..16777215";
                }
                units "microseconds";
                description
                  "Minimum unidirectional link delay (RFC 7471 §4.2,
                   sub-TLV 14). Advertised with max-delay; the Min/Max
                   sub-TLV is emitted only when both are set.";
              }
              leaf max-delay {
                ext:help "Maximum unidirectional link delay (us)";
                type uint32 {
                  range "0..16777215";
                }
                units "microseconds";
                description
                  "Maximum unidirectional link delay (RFC 7471 §4.2,
                   sub-TLV 14).";
              }
              leaf delay-variation {
                ext:help "Unidirectional delay variation / jitter (us)";
                type uint32 {
                  range "0..16777215";
                }
                units "microseconds";
                description
                  "Unidirectional delay variation / jitter (RFC 7471
                   §4.3, sub-TLV 15).";
              }
              leaf loss {
                ext:help "Unidirectional link loss ratio";
                type uint32 {
                  range "0..16777214";
                }
                description
                  "Unidirectional link loss (RFC 7471 §4.4, sub-TLV 16),
                   encoded in units of 0.000003 %; the maximum 16777214
                   (0xFFFFFE) is ~50.33 %.";
              }
              container measurement {
                ext:help "Measure this link's delay and loss dynamically (STAMP, RFC 8762)";
                description
                  "Active performance measurement of this link. When
                   enabled, a STAMP Session-Sender (RFC 8762,
                   unauthenticated) probes the P2P neighbor once the
                   adjacency reaches Full; the damped min/max/avg delay
                   and delay variation populate the same te-metric
                   fields as static configuration (a static leaf, when
                   set, overrides the measured value per field). The
                   probes are answered by the neighbor's implicit
                   Session-Reflector, so measurement must be enabled on
                   both ends of the link.";
                leaf enabled {
                  ext:help "Activate measurement on this interface";
                  type boolean;
                  description "Activate measurement on this interface.";
                }
                leaf interval {
                  ext:help "Probe transmit interval in milliseconds";
                  type uint32 {
                    range "100..60000";
                  }
                  units "milliseconds";
                  description "Probe transmit interval. Default 1000 ms.";
                }
                leaf damping-period {
                  ext:help "Minimum spacing between IGP exports (s)";
                  type uint32 {
                    range "1..3600";
                  }
                  units "seconds";
                  description
                    "Minimum spacing between exports to the IGP; each
                     period's samples form the advertised min/max/avg
                     window. Default 30 s.";
                }
                leaf anomaly-threshold {
                  ext:help "Average delay at/above which the Anomalous bit is set (us)";
                  type uint32 {
                    range "0..16777215";
                  }
                  units "microseconds";
                  description
                    "Upper bound for the measured average one-way delay. At or
                     above it, the Anomalous (A) bit is set on the delay
                     sub-TLVs this link advertises (RFC 7471 §4.1 and §4.2), telling
                     receivers the link has degraded past what the operator
                     accepts. Only measured values carry the bit: a delay
                     pinned by the sibling static leaves is always advertised
                     with it clear. Unset disables anomaly detection.";
                }
                leaf reuse-threshold {
                  ext:help "Average delay below which the Anomalous bit clears (us)";
                  type uint32 {
                    range "0..16777215";
                  }
                  units "microseconds";
                  description
                    "Lower bound at which a set Anomalous bit clears again.
                     Between this and anomaly-threshold the bit holds its
                     current state, so a link resting on the bound does not
                     re-originate every export period. Values above
                     anomaly-threshold are clamped to it. Unset means no
                     hysteresis band: anomaly-threshold both sets and clears.";
                }
                leaf reflector {
                  ext:help "How this router reflects the peer's probes (default stateless)";
                  type enumeration {
                    enum stateless;
                    enum stateful;
                  }
                  description
                    "stateless (the default, RFC 8762 section 4.3): replies copy the
                     sender's sequence number. stateful: replies carry this router's own
                     per-peer sequence counter, which lets a peer that declares
                     'loss peer-reflector stateful' tell forward loss from reverse. On if
                     any IGP measuring this link sets it.";
                }
                container loss {
                  ext:help "Measured link loss (RFC 8570 / RFC 7471 section 4.4)";
                  description
                    "Round-trip probe loss, measured on the same STAMP session
                     and advertised as the unidirectional link-loss sub-TLV. On
                     by default wherever measurement is enabled. Loss runs on
                     its own 30 s bucket clock, independent of damping-period. A
                     static te-metric loss, when set, overrides the measured
                     value.";
                  leaf enabled {
                    ext:help "Advertise measured loss (default true)";
                    type boolean;
                    description "Advertise measured loss. Default true.";
                  }
                  leaf interval {
                    ext:help "Loss averaging and advertisement interval (s, multiple of 30)";
                    type uint32 {
                      range "30..3600";
                    }
                    units "seconds";
                    description
                      "Loss is averaged over the last interval, and re-advertised
                       at most once per interval. Must be a multiple of 30.
                       Default 120 s.";
                  }
                  leaf threshold {
                    ext:help "Re-advertise on a change of this percent of the advertised value";
                    type uint32 {
                      range "0..100";
                    }
                    units "percent";
                    description
                      "A periodic re-advertisement needs a change of at least this
                       percentage of the advertised value, and at least
                       minimum-change. Default 10.";
                  }
                  leaf minimum-change {
                    ext:help "Re-advertise only on a change of at least this many percentage points";
                    type decimal64 {
                      fraction-digits 6;
                    }
                    units "percent";
                    description
                      "The smallest absolute change, in percentage points, that is
                       re-advertised. It also governs changes to and from zero.
                       At the default probe rate one lost probe is 0.83 %, so a
                       smaller value lets single-probe noise re-flood. Default 1.0.";
                  }
                  leaf accelerated-threshold {
                    ext:help "Advertise at once when the latest 30 s differs by this many points";
                    type decimal64 {
                      fraction-digits 6;
                    }
                    units "percent";
                    description
                      "When the latest 30 s bucket alone differs from the
                       advertised value by at least this many percentage points,
                       advertise that value at once instead of waiting for the
                       interval. Unset (the default) disables acceleration.";
                  }
                  leaf integrity {
                    ext:help "Minimum percent of expected probes for a window to be trusted";
                    type uint32 {
                      range "1..100";
                    }
                    units "percent";
                    description
                      "A loss window is advertised only when at least this
                       percentage of the probes the probe interval should have
                       produced actually settled. Default 90.";
                  }
                  leaf anomaly-threshold {
                    ext:help "Set the Anomalous bit at or above this loss (percent)";
                    type decimal64 {
                      fraction-digits 6;
                    }
                    units "percent";
                    description
                      "Loss, in percent, at or above which the link-loss sub-TLV's
                       Anomalous (A) bit is set, evaluated on the value it is advertised
                       with (RFC 8570 / RFC 7471 section 4.4). Unset (the default) never
                       sets the bit.";
                  }
                  leaf reuse-threshold {
                    ext:help "Clear the Anomalous bit after a loss interval below this loss (percent)";
                    type decimal64 {
                      fraction-digits 6;
                    }
                    units "percent";
                    description
                      "Loss, in percent, below which the Anomalous bit clears once the
                       loss has stayed below it for a whole loss interval. Defaults to,
                       and is capped at, anomaly-threshold.";
                  }
                  leaf peer-reflector {
                    ext:help "How the peer reflects this router's probes (default stateless)";
                    type enumeration {
                      enum stateless;
                      enum stateful;
                    }
                    description
                      "Declares the peer's reflector mode; it cannot be detected.
                       stateless (the default): the advertised loss is round-trip, an upper
                       bound on forward loss. stateful: the peer reflects with its own
                       sequence counter (a zebra-rs peer with 'measurement reflector
                       stateful', a Juniper peer with stateful-sequence), losses are split
                       by direction, and forward loss is advertised. Declaring a stateless
                       peer stateful makes every loss read as reverse.";
                  }
                }
              }
            }
            leaf-list affinity {
              ext:help "Affinity (admin-group) names on this link";
              // Names of /affinity-map entries this link carries.
              // Advertised as an Extended Admin Group bitmap inside the
              // RFC 9492 ASLA sub-TLV on the E-Router-LSA Router-Link
              // TLV and tested against each FAD's include/exclude
              // constraints at flex-algo SPF time.
              type string;
            }
          }
        }
        container segment-routing {
          ext:help "Segment Routing (SR-MPLS / SRv6) configuration";
          // Mirrors `router isis / segment-routing` (config.yang L516).
          // OSPFv3 carries SR over both dataplanes: MPLS (RFC 8666 via
          // E-LSAs) and SRv6 (RFC 9513). As with IS-IS, the two are
          // mutually exclusive — one instance advertises either SR-MPLS
          // SIDs or an SRv6 locator, never both — so they form a
          // `choice`: committing `srv6` implicitly deletes a configured
          // `mpls` (and vice versa) per RFC 7950 §7.9.3, and the commit
          // diff tears the old dataplane down exactly as an explicit
          // delete would.
          choice dataplane {
            case mpls {
              container mpls {
                ext:help "Segment Routing over MPLS dataplane";
                presence "Enable Segment Routing over MPLS dataplane";
              }
            }
            case srv6 {
              container srv6 {
                ext:help "Segment Routing over IPv6 dataplane (SRv6)";
                presence "Enable Segment Routing over IPv6 dataplane";
                leaf locator {
                  ext:help "Global SRv6 locator name for this instance";
                  // Name of a locator defined under the global
                  // /segment-routing/locator list. Held as a string (not a
                  // leafref) so an OSPFv3 config can be staged before the
                  // global locator is committed — matches the IS-IS
                  // staging convention (config.yang L524).
                  type string;
                }
              }
            }
          }
        }

        list flex-algo {
          ext:help "Flexible Algorithm definitions (RFC 9350)";
          // OSPFv3 Flexible Algorithm (RFC 9350 §7) definition. Shape
          // mirrors `router ospf / flex-algo`; keyed by the on-the-wire
          // numeric identifier (128..255). `advertise-definition true`
          // causes this router to originate the FAD TLV in its
          // E-Router-LSA (RFC 9350 §7.1, OSPFv3 FAD TLV 16); without it
          // the router participates using a FAD learned from another
          // node. At least one (preferably two) routers per area MUST
          // advertise the definition.
          key "algo";
          leaf algo {
            ext:help "Flex-Algorithm identifier (128..255)";
            type uint8 { range "128..255"; }
            description
              "Flex-Algorithm identifier (RFC 9350 §4). 0..127 are
               reserved by IANA; 128..255 are user-defined.";
          }

          leaf advertise-definition {
            ext:help "Originate the FAD TLV for this algorithm";
            type boolean;
            default false;
            description
              "When true, originate the FAD TLV for this algorithm in
               the E-Router-LSA. If no router in the area advertises the
               FAD, every participant fails to compute paths.";
          }

          leaf metric-type {
            ext:help "FAD metric type (igp / delay / te-default)";
            type enumeration {
              enum igp;                   // FAD Metric-Type 0
              enum min-unidir-link-delay; // FAD Metric-Type 1 (RFC 8570)
              enum te-default;            // FAD Metric-Type 2 (RFC 5305)
            }
            default igp;
          }

          leaf priority {
            ext:help "FAD advertisement priority (higher wins)";
            // FAD Priority (RFC 9350 §6.5). Tie-breaker when more than
            // one router originates a FAD for the same algo; higher
            // priority wins.
            type uint8;
            default 128;
          }

          leaf prefix-metric {
            ext:help "Include advertised flex-algo prefix metric";
            // M-flag in the FAD Flags sub-TLV (RFC 9350 §6.4). When set,
            // the computed path metric to a prefix includes the
            // advertised Flexible Algorithm Prefix Metric.
            type boolean;
            default false;
          }

          container dataplane {
            ext:help "Per-algorithm dataplane participation";
            // Per-algorithm dataplane participation. OSPFv3 flex-algo
            // forwards over SR-MPLS (per-algo Prefix-SID labels); the
            // `ip` flag selects plain IPv6 forwarding for the algo's
            // computed paths.
            leaf sr-mpls {
              ext:help "Forward this algorithm over SR-MPLS";
              type boolean; default false; }
            leaf ip      {
              ext:help "Forward this algorithm over plain IPv6";
              type boolean; default false; }
          }

          container affinity {
            ext:help "FAD affinity (admin-group) constraints";
            // FAD Exclude / Include-Any / Include-All Admin Group
            // sub-TLVs (RFC 9350 §6.2-6.4). Each leaf-list value is a
            // name from the global /affinity-map table.
            leaf-list include-any {
              ext:help "Include links with any of these affinities";
              type string; }
            leaf-list include-all {
              ext:help "Include links with all of these affinities";
              type string; }
            leaf-list exclude-any {
              ext:help "Exclude links with any of these affinities";
              type string; }
          }

          leaf-list srlg-exclude {
            ext:help "Exclude links in these SRLG groups";
            // FAD Exclude SRLG sub-TLV (RFC 9350 §6.5). Each entry
            // references a /srlg/group name.
            type string;
          }

          container fast-reroute {
            ext:help "Per-flex-algo fast-reroute";
            // Per-algorithm fast-reroute OPT-OUT; same model and rationale
            // as `router isis / flex-algo / fast-reroute`. TI-LFA
            // enablement is instance-level
            // (/router/ospfv3/fast-reroute/ti-lfa) and every algorithm
            // this router participates in inherits it. The per-algorithm
            // computation itself is still deferred for OSPFv3 — the leaf
            // is accepted and stored so the schema stays uniform across
            // IS-IS / OSPFv2 / OSPFv3, but nothing consumes it yet.
            leaf disable {
              ext:help "Disable fast-reroute for this flex-algo";
              type empty;
              description
                "Suppress TI-LFA repair computation and installation for
                 this Flex-Algorithm only; algorithm 0 and every other
                 algorithm keep whatever /router/ospfv3/fast-reroute/ti-lfa
                 configures.";
            }
          }
        }

        container fast-reroute {
          ext:help "Fast-reroute / TI-LFA protection (RFC 9855)";
          // OSPFv3 fast-reroute mechanisms (RFC 7490 LFA family).
          // Same shape as `router ospf / fast-reroute`; the repair is
          // expressed as SR-MPLS labels, so segment-routing/mpls must
          // also be enabled for the dataplane install.
          container ti-lfa {
            ext:help "Topology-Independent LFA (TI-LFA)";
            // Topology-Independent Loop-Free Alternate (TI-LFA,
            // RFC 9855). Post-convergence repair over the v3 LSDB.
            presence "Enable Topology-Independent LFA (TI-LFA)";

            container compute-mode {
              ext:help "How the TI-LFA computation is scheduled";
              // Same modes and semantics as `router ospf
              // fast-reroute ti-lfa compute-mode`. One keyword per
              // mode under a `choice`; the shard count nests under
              // `sharding`. The default mode (serial) is applied by
              // the Rust handler.
              choice mode {
                case serial {
                  leaf serial {
                    ext:help "Run on the SPF worker thread";
                    type empty;
                  }
                }
                case conservative {
                  leaf conservative {
                    ext:help "Fan out one task per destination";
                    type empty;
                  }
                }
                case aggressive {
                  leaf aggressive {
                    ext:help "Also share the PC-path SPF per protected node";
                    type empty;
                  }
                }
                case sharding {
                  container sharding {
                    ext:help "Aggressive work split into parallel shards";
                    presence "Shard the aggressive computation (default 8 shards)";
                    // Hard upper bound on TI-LFA parallelism, consulted
                    // only in this mode. Bare `sharding` uses 8
                    // (applied by the handler).
                    leaf shards {
                      ext:help "Max parallel TI-LFA shards";
                      type uint16 {
                        range "1..256";
                      }
                      default "8";
                    }
                  }
                }
              }
            }
          }
          container backup-as-primary {
            ext:help "Install TI-LFA backup as the primary nexthop";
            // Swap the metric-sort offset between the SPF primary and
            // the TI-LFA repair so the repair installs first. Protection
            // testing knob; see `router ospf` for the full rationale.
            presence "Install TI-LFA backup as the primary nexthop";
          }
        }

        list vrf {
          ext:help "Per-VRF OSPFv3 instance";
          // Per-VRF OSPFv3 instance. See `container ospf`'s `vrf`
          // list for the forwarding model. Exposes the per-interface
          // knobs the v3 instance handles (enabled / network-type /
          // priority / timers) plus `router-id` (the forwarded line
          // hits the same `/router/ospfv3/router-id` callback on the
          // child). `redistribute` stays omitted — the v3 instance
          // has no config handler for it today (a forwarded line
          // would be a no-op).
          key "name";
          leaf name {
            ext:help "VRF instance name";
            ext:dynamic "rib:vrf";
            type string;
          }
          leaf router-id {
            ext:help "OSPFv3 router identifier for this VRF";
            type inet:ipv4-address;
          }
          // Instance-level redistribution, forwarded to the per-VRF v3
          // instance (prefix stripped). `redistribute bgp` injects the
          // VPNv6 routes imported into this VRF into the CE-facing OSPFv3
          // (the L3VPN PE-CE down direction).
          container redistribute {
            ext:help "Redistribute external routes into OSPFv3";
            container bgp {
              ext:help "Redistribute BGP routes as AS-External LSAs";
              presence "Redistribute BGP routes as AS-External (Type-5) LSAs";
              leaf metric {
                ext:help "Metric for redistributed BGP routes";
                type uint32 {
                  range "0..16777214";
                }
                default 20;
              }
              leaf metric-type {
                ext:help "AS-External metric type (type-1 / type-2)";
                type enumeration {
                  enum type-1;
                  enum type-2;
                }
                default type-2;
              }
            }
          }
          list area {
            ext:help "OSPFv3 area for this VRF";
            key "area-id";
            leaf area-id {
              ext:help "Area identifier (dotted or decimal)";
              type union {
                type uint32;
                type inet:ipv4-address;
              }
            }
            list interface {
              ext:help "Interface in this OSPFv3 area";
              key "if-name";
              leaf if-name {
                ext:help "Interface name";
                ext:dynamic "rib:interface";
                type string;
              }
              leaf enabled {
                ext:help "Enable OSPFv3 on this interface";
                type boolean;
              }
              leaf network-type {
                ext:help "Interface network type (broadcast / p2p)";
                type enumeration {
                  enum broadcast;
                  enum point-to-point;
                }
              }
              leaf priority {
                ext:help "Router priority for DR/BDR election";
                type uint8;
              }
              leaf hello-interval {
                ext:help "Hello packet interval in seconds";
                type uint16;
              }
              leaf dead-interval {
                ext:help "Neighbor dead interval in seconds";
                type uint32;
              }
              leaf retransmit-interval {
                ext:help "LSA retransmit interval in seconds";
                type uint16;
              }
              leaf mtu-ignore {
                ext:help "Ignore MTU mismatch in DBD packets";
                type boolean;
              }
            }
          }
        }
      }
      container isis {
        ext:help "IS-IS routing protocol configuration";
        presence "Enables configuration of IS-IS";
        leaf net {
          ext:help "Network Entity Title (area address + system-id)";
          // First entry in "router isis" node.
          ext:sort "1";
          type isis:net;
        }

        container distribute {
          ext:help "Control installing IS-IS routes into the RIB";
          leaf rib {
            ext:help "Install IS-IS routes into the RIB";
            type boolean;
          }
        }

        container bfd {
          ext:help "BFD defaults for this IS-IS instance";
          description
            "Instance-level BFD defaults applied to every IS-IS
             interface, overridable per interface. `enabled true` here
             blanket-enables BFD on all of the instance's interfaces; a
             per-interface `bfd { enabled false }` opts one out. Each leaf
             is overridable per interface.";
          leaf enabled {
            ext:help "Blanket-enable BFD on all IS-IS interfaces";
            type boolean;
            description
              "When true, attach BFD to every IS-IS interface's
               adjacencies (overridable per interface).";
          }
          leaf echo-mode {
            ext:help "Default BFD Echo role (transmit | receive | both)";
            type enumeration {
              enum transmit { description "Originate Echo only."; }
              enum receive { description "Advertise + reflect only."; }
              enum both { description "Both."; }
            }
            description
              "Instance-default BFD Echo role for every interface
               (RFC 5880 §6.4; single-hop, IPv4 or IPv6). Overridable
               per interface; absent ⇒ Echo off.";
          }
          leaf echo-transmit-interval {
            ext:help "Default Echo transmit interval (ms)";
            type uint32;
            units "milliseconds";
          }
          leaf echo-receive-interval {
            ext:help "Default advertised Required Min Echo RX (ms)";
            type uint32;
            units "milliseconds";
          }
          leaf detect-offload {
            ext:help "Default: offload expiration detection to XDP (kernel)";
            type boolean;
            description
              "Instance default for offloading control-packet expiration
               detection (RFC 5880 §6.8.4) to the per-interface XDP/eBPF
               helper once a session is Up. Overridable per interface;
               absent ⇒ false (detection in userspace).";
          }
        }

        leaf is-type {
          ext:help "IS-IS level for this instance (L1 / L1-2 / L2-only)";
          type enumeration {
            enum level-1;
            enum level-1-2;
            enum level-2-only;
          }
        }

        container area-proxy {
          ext:help "Area Proxy (RFC 9666) — present the L1 area as one L2 node";
          presence "Enable Area Proxy participation";
          description
            "RFC 9666 Area Proxy participation. Configure on every Inside
             Router: the router advertises the Area Proxy TLV in its L2
             LSP fragment 0 as the readiness signal. A router additionally
             configured with a proxy-system-id is an Area Leader candidate
             (RFC 9667 election: highest priority wins, ties broken by
             highest system-id); the elected leader distributes the Proxy
             System ID to the area once every inside router is ready. All
             candidates SHOULD be configured with the same proxy-system-id
             so a leadership change keeps the proxy identity stable.";
          leaf proxy-system-id {
            ext:help "Proxy System ID representing the entire area";
            // Not `isis:system-id`: imported typedefs resolve through
            // the fixed table in config/parse.rs `ytype_from_typedef`,
            // which doesn't carry it — an unresolved typedef leaf
            // matches nothing (cf. the `clear isis neighbor` id leaf).
            // The inline pattern gives the same anchored `xxxx.xxxx.xxxx`
            // validation at set time.
            type string {
              pattern '[0-9A-Fa-f.]+';
            }
          }
          leaf priority {
            ext:help "Area Leader election priority (default 64)";
            type uint8;
          }
          leaf hostname {
            ext:help "Dynamic Hostname advertised in the Proxy LSP";
            // Same RFC 1123-ish charset as the system hostname leaf.
            type string {
              pattern "[A-Za-z0-9][A-Za-z0-9.-]*";
            }
          }
          container area-sid {
            ext:help "Anycast Area SID representing the entire area (RFC 9666)";
            description
              "RFC 9666 §4.3.2 Area SID: an anycast prefix + SID index
               the Area Leader distributes in its Area Proxy TLV and
               advertises as a Node SID in the Proxy LSP. Every Inside
               Edge Router installs a pop for SRGB-start + index, so a
               packet carrying the SID is delivered to whichever edge
               router receives it and the SID is consumed. Configure
               identically on every Area Leader candidate.";
            leaf prefix {
              ext:help "Anycast IPv4 prefix for the Area SID";
              type inet:ipv4-prefix;
            }
            leaf index {
              ext:help "SID index into the SRGB";
              type uint32;
            }
          }
        }

        container segment-routing {
          ext:help "Segment Routing (SR-MPLS / SRv6) configuration";
          // The two dataplanes are mutually exclusive: one IS-IS
          // instance advertises either SR-MPLS SIDs or an SRv6 locator,
          // never both. Modelled as a `choice`, so committing
          // `segment-routing srv6 ...` implicitly deletes a configured
          // `segment-routing mpls` (and vice versa) per RFC 7950
          // §7.9.3 — the commit diff then tears the old dataplane down
          // exactly as an explicit delete would.
          choice dataplane {
            case mpls {
              container mpls {
                ext:help "Segment Routing over MPLS dataplane";
                presence "Enable Segment Routing over MPLS dataplane";
                leaf no-local-prefix-sid {
                  ext:help "Skip the local Prefix-SID label";
                  type empty;
                  description
                    "Suppress installing the local (self-originated)
                     Prefix-SID label into the MPLS forwarding table (LFIB).
                     By default (leaf absent) the local node-SID is installed
                     as a pop entry so traffic arriving with this node's own
                     node-SID label is delivered locally, matching IOS-XR /
                     SR-OS. When present, only remote prefix-SIDs and
                     adjacency-SIDs are installed. Only effective while
                     SR-MPLS is enabled.";
                }
              }
            }
            case srv6 {
              container srv6 {
                ext:help "Segment Routing over IPv6 dataplane (SRv6)";
                presence "Enable Segment Routing over IPv6 dataplane";
                leaf locator {
                  ext:help "Global SRv6 locator name for this instance";
                  // Name of a locator defined under the global
                  // /segment-routing/locator list. Held as a string (not a
                  // leafref) so an IS-IS config can be staged before the
                  // global locator is committed.
                  type string;
                }
                list flex-algo-locator {
                  ext:help "Per-flex-algo SRv6 locator binding";
                  // Per-Flex-Algorithm SRv6 locator binding. The named
                  // locator is advertised in SRv6 Locator TLV 27 with the
                  // Algorithm field set to `algo` (RFC 9352 §7.1). The
                  // base `locator` leaf above carries algorithm 0 (regular
                  // SPF); flex-algos (128..255) bind here. As with the
                  // base leaf, the locator name is a plain string so the
                  // IS-IS config can be staged before the matching
                  // /segment-routing/locator entry is committed.
                  key "algo";
                  leaf algo {
                    ext:help "Flex-Algorithm identifier (128..255)";
                    type uint8 { range "128..255"; }
                  }
                  leaf locator {
                    ext:help "SRv6 locator name for this algorithm";
                    type string;
                  }
                }
              }
            }
          }
        }

        list flex-algo {
          ext:help "Flexible Algorithm definitions (RFC 9350)";
          // IS-IS Flexible Algorithm (RFC 9350) definition. Each list
          // entry describes one algorithm this router participates in
          // and is keyed by the on-the-wire numeric identifier
          // (FRR / Cisco IOS-XR style: `flex-algo 128`). The same
          // numeric value keys per-interface `flex-algo-prefix-sid`
          // and SRv6 `flex-algo-locator` bindings — a single
          // identifier ties FAD config, per-link SIDs and the value
          // emitted in the FAD sub-TLV's Flex Algorithm field.
          // `advertise-definition true` causes the router to
          // originate the FAD sub-TLV inside Router Capability TLV
          // 242; without it the router participates using a FAD
          // learned from another node — at least one (preferably
          // two) routers per area MUST advertise.
          key "algo";
          leaf algo {
            ext:help "Flex-Algorithm identifier (128..255)";
            type uint8 { range "128..255"; }
            description
              "Flex-Algorithm identifier (RFC 9350 §4). 0..127 are
               reserved by IANA; 128..255 are user-defined.";
          }

          leaf advertise-definition {
            ext:help "Originate the FAD sub-TLV";
            type boolean;
            default false;
            description
              "When true, originate the FAD sub-TLV for this
               algorithm. If no router in the area advertises the
               FAD, every participant fails to compute paths.";
          }

          leaf metric-type {
            ext:help "FAD metric type (igp / delay / te-default)";
            type enumeration {
              enum igp;                   // FAD Metric-Type 0
              enum min-unidir-link-delay; // FAD Metric-Type 1 (RFC 8570)
              enum te-default;            // FAD Metric-Type 2 (RFC 5305)
            }
            default igp;
          }

          leaf priority {
            ext:help "FAD advertisement priority (higher wins)";
            // FAD Priority (RFC 9350 §5.1). Tie-breaker when more
            // than one router originates a FAD for the same algo;
            // higher priority wins.
            type uint8;
            default 128;
          }

          leaf prefix-metric {
            ext:help "Include advertised flex-algo prefix metric";
            // M-flag in the FAD Flags sub-TLV (RFC 9350 §6.4).
            // When set, the computed path metric to a prefix
            // includes the advertised prefix metric in addition
            // to the path metric.
            type boolean;
            default false;
          }

          container dataplane {
            ext:help "Per-algorithm dataplane participation";
            // Per-algorithm dataplane participation. Explicit flags
            // (FRR style) so the FAD sub-TLV bits, the SPF graph
            // filter, and the SID-install path can all be driven
            // from configuration rather than inferred from which
            // SIDs happen to be present.
            leaf sr-mpls {
              ext:help "Forward this algorithm over SR-MPLS";
              type boolean; default false; }
            leaf srv6    {
              ext:help "Forward this algorithm over SRv6";
              type boolean; default false; }
            leaf ip      {
              ext:help "Forward this algorithm over plain IP";
              type boolean; default false; }
          }

          container affinity {
            ext:help "FAD affinity (admin-group) constraints";
            // FAD Exclude / Include-Any / Include-All Affinity
            // sub-TLVs (RFC 9350 §6.1). Each leaf-list value is a
            // name from this instance's /affinity-map table.
            leaf-list include-any {
              ext:help "Include links with any of these affinities";
              type string; }
            leaf-list include-all {
              ext:help "Include links with all of these affinities";
              type string; }
            leaf-list exclude-any {
              ext:help "Exclude links with any of these affinities";
              type string; }
          }

          leaf-list srlg-exclude {
            ext:help "Exclude links in these SRLG groups";
            // FAD Exclude SRLG sub-TLV (RFC 9350 §6.2). Each entry
            // references a /srlg/group name; the per-link SRLG
            // memberships configured under
            // /router/isis/interface/srlg drive the actual link
            // exclusion at SPF time.
            type string;
          }

          leaf exclude-max-link-loss {
            ext:help "Exclude links whose advertised loss exceeds this percentage";
            // FAD Exclude Maximum Link Loss sub-TLV (FAEML,
            // draft-ietf-lsr-flex-algo-link-loss), advertised with the
            // definition in the draft's placeholder type 252 until IANA
            // assigns one. Rounded to the nearest RFC 8570 unit of
            // 0.000003 %; the range and precision are checked at commit.
            type decimal64 {
              fraction-digits 6;
            }
            units "percent";
            description
              "Prune from this algorithm's topology every link whose
               advertised unidirectional link loss (RFC 8570) is greater
               than this percentage, 0 to 50.331642. A link that
               advertises no loss is kept. Loss is compared as the
               definition's winner advertises it, so the setting takes
               effect only where this router's definition wins.";
          }

          container fast-reroute {
            ext:help "Per-flex-algo fast-reroute";
            // Per-algorithm fast-reroute OPT-OUT. TI-LFA enablement is an
            // instance-level property (/router/isis/fast-reroute/ti-lfa):
            // once on, every algorithm this router participates in is
            // protected, with each algorithm's repair computed inside its
            // own constrained topology and expressed with that
            // algorithm's SIDs. That inheritance is what RFC 9350 §12
            // requires — a repair built from algorithm-0 segments can
            // traverse a link the FAD excluded, defeating the constraint
            // the algorithm exists to enforce.
            //
            // Matches the industry model: IOS-XR enables TI-LFA per
            // interface and offers only `flex-algo <n> fast-reroute
            // disable`; Juniper and FRR have no per-algorithm knob at all
            // and simply protect every slice. An opt-IN toggle here would
            // leave an operator who configured `fast-reroute ti-lfa` with
            // silently unprotected flex-algo traffic.
            leaf disable {
              ext:help "Disable fast-reroute for this flex-algo";
              type empty;
              description
                "Suppress TI-LFA repair computation and installation for
                 this Flex-Algorithm only; algorithm 0 and every other
                 algorithm keep whatever /router/isis/fast-reroute/ti-lfa
                 configures. Use where a repair is worse than a drop — a
                 low-latency slice whose post-convergence repair still
                 satisfies the FAD constraints but blows the latency
                 budget the slice exists to guarantee.";
            }
          }
        }

        container fast-reroute {
          ext:help "Fast-reroute / TI-LFA protection (RFC 9855)";
          // IS-IS fast-reroute mechanisms. Empty container is a no-op;
          // the per-mechanism child presence containers turn features on.
          container ti-lfa {
            ext:help "Topology-Independent LFA (TI-LFA)";
            // Topology-Independent Loop-Free Alternate (TI-LFA, RFC 9855).
            // Computes a post-convergence repair path expressed as
            // SR-MPLS labels, so segment-routing/mpls must also be
            // enabled for the repair to install in the dataplane.
            presence "Enable Topology-Independent LFA (TI-LFA)";

            container compute-mode {
              ext:help "How the TI-LFA computation is scheduled";
              // Execution scheduling for the per-destination TI-LFA
              // computation (design: docs/design/isis-tilfa-parallel-
              // spf.md). Results are identical across modes — only CPU
              // usage and wall-clock differ. `serial` runs on the SPF
              // worker thread; `conservative` fans out one task per
              // destination; `aggressive` additionally shares the
              // PC-path SPF across destinations behind the same
              // protected node; `sharding` is the aggressive work
              // split into at most `shards` parallel shards.
              //
              // Modelled as a `choice` of one keyword per mode (the
              // shard count nests under `sharding`, the only mode it
              // applies to). The cases are mutually exclusive: setting
              // one case auto-clears its siblings from the candidate
              // store (RFC 7950 §7.9.3), so a case switch commits as
              // delete(old) + set(new). The default mode (serial) is
              // applied by the Rust handler — a choice/case carries no
              // YANG default.
              choice mode {
                case serial {
                  leaf serial {
                    ext:help "Run on the SPF worker thread";
                    type empty;
                  }
                }
                case conservative {
                  leaf conservative {
                    ext:help "Fan out one task per destination";
                    type empty;
                  }
                }
                case aggressive {
                  leaf aggressive {
                    ext:help "Also share the PC-path SPF per protected node";
                    type empty;
                  }
                }
                case sharding {
                  container sharding {
                    ext:help "Aggressive work split into parallel shards";
                    presence "Shard the aggressive computation (default 8 shards)";
                    // Hard upper bound on TI-LFA parallelism — lets an
                    // operator reserve cores for other daemons on a
                    // shared box. Bare `sharding` uses 8 (applied by
                    // the handler; libyang does not carry the leaf
                    // `default` into the entry tree).
                    leaf shards {
                      ext:help "Max parallel TI-LFA shards";
                      type uint16 {
                        range "1..256";
                      }
                      default "8";
                    }
                  }
                }
              }
            }
          }
          container micro-loop-avoidance {
            ext:help "Delay IS-IS convergence after local TI-LFA activation";
            presence "Enable IS-IS micro-loop avoidance";
            description
              "Retain eligible native IPv4 and IPv6 routes on their
               activated TI-LFA repair for a fixed interval after a local
               failure. Withdrawals, new prefixes, unrelated routes,
               Flex-Algorithm routes, and MPLS ILM updates are not delayed.";
            leaf rib-update-delay {
              ext:help "Post-failure native RIB update delay (milliseconds)";
              type uint32 {
                range "1..60000";
              }
              units milliseconds;
              default "5000";
            }
          }
          container backup-as-primary {
            ext:help "Install TI-LFA backup as the primary nexthop";
            // Swap the metric-sort offset between the SPF primary
            // nexthop and the TI-LFA repair: the repair installs at
            // route.metric (sorted first), and the primary installs
            // at route.metric + BACKUP_METRIC_OFFSET. Lets operators
            // pin traffic onto the TI-LFA path for protection
            // testing without rewiring the topology.
            presence "Install TI-LFA backup as the primary nexthop";
          }
        }

        container egress-protection {
          ext:help "Mirror SID egress node/link protection (SRv6/SR-MPLS)";
          leaf hold-down {
            ext:help "Stale-route retention hold-down in seconds";
            type uint32;
            units seconds;
            description
              "Node-protection stale-route retention hold-down. After a
               protected egress's node fails, its locator is kept alive as
               a seg6 H.Encaps backup to the protector's Mirror SID; this
               bounds how long that backup forwards before it is withdrawn
               (so a genuinely-decommissioned egress is not masked toward
               the protector forever). 0 or unset = no hold-down: the
               backup floats for as long as the protector advertises.";
          }
          // draft-ietf-rtgwg-srv6-egress-protection / RFC 8679. This
          // node (the protector, PEB) advertises a Mirror SID (End.M
          // for SRv6) plus the protected egress's locator(s) so a PLR
          // can redirect traffic past a failed egress PE or PE-CE link
          // — the gap TI-LFA cannot cover. Each `protect` entry
          // declares one egress this node backs up. Phase 2 scope:
          // config + state only; nothing is advertised or installed
          // until later phases.
          list protect {
            ext:help "Protect one egress node, keyed by its SRv6 locator";
            key "protected-locator";
            leaf protected-locator {
              ext:help "Prefix of the protected egress PE";
              type inet:ip-prefix;
              description
                "Prefix identifying the protected egress PE (PEA). For
                 SRv6 it is PEA's SRv6 locator (IPv6), e.g.
                 2001:db8:a3:1::/64, emitted in the Protected Locators
                 sub-sub-TLV of the Mirror SID sub-TLV. For SR-MPLS it is
                 PEA's IGP loopback (IPv4 in the current SR-MPLS dataplane,
                 which has no IPv6 prefix-SID), e.g. 1.1.1.3/32, emitted as
                 the FEC of the SID/Label Binding TLV (149). The PLR /
                 protected egress matches it to identify PEA.";
            }
            leaf mirror-sid {
              ext:help "Mirror SID (End.M) to advertise";
              type inet:ipv6-address;
              description
                "Mirror SID (End.M) to advertise for the protected
                 egress. Must lie within this node's own SRv6 locator.
                 When omitted, a SID is auto-allocated from the local
                 locator at origination time.";
            }
            leaf via-vrf {
              ext:help "Local VRF that reaches the protected CE";
              type string;
              description
                "Name of the local VRF whose forwarding reaches the
                 dual-homed CE. The mirror-context FIB resolves the
                 protected egress's service SIDs in this VRF (static
                 path; the BGP-learned path lands in a later phase).";
            }
            leaf dataplane {
              ext:help "Dataplane this entry protects (srv6 / mpls)";
              type enumeration {
                enum srv6;
                enum mpls;
              }
              default "srv6";
              description
                "Dataplane this entry protects. srv6 advertises the
                 End.M Mirror SID sub-TLV in the SRv6 Locator TLV; mpls
                 advertises the SID/Label Binding TLV (149) M-flag
                 (SR-MPLS, wired in a later phase).";
            }
          }
        }

        container graceful-restart {
          ext:help "Graceful restart helper / restarter (RFC 5306)";
          // RFC 5306 helper and restarter configuration. Defaults
          // match FRR: helper enabled out of the box (transparent /
          // lossless), restarter OFF until the exit-wiring (Phase
          // 5d) + restart-aware boot (5e) make the full path safe.
          // Restarter capability advertised on the wire without the
          // exit path would tear down routes on every restart while
          // still claiming GR to peers — worse than no GR.
          leaf helper-enabled {
            ext:help "Act as graceful-restart helper for peers";
            type boolean;
            default true;
            description
              "Honor a peer's Restart TLV (RFC 5306). When true, an
               IIH with RR=1 from an Up adjacency maintains the
               adjacency, suppresses the hold-timer refresh on
               retransmitted RR (RFC §3.2(a)), and triggers the §3.2(b)
               RA reply plus an immediate CSNP+SRM kick on LANs where
               we are the elected helper. When false, every Restart
               TLV is observed for `show isis graceful-restart` but no
               adjacency-state side effects occur — IIH+RR is
               treated as any other IIH.";
          }
          leaf restarter-enabled {
            ext:help "Act as the graceful-restart restarter";
            type boolean;
            default false;
            description
              "Allow this instance to act as the restarter side of
               RFC 5306 graceful restart. When true, an operator-
               triggered `clear isis graceful-restart begin` floods
               IIH+RR on every Up interface and freezes self-LSP
               refresh. When false, the `clear` is a no-op — until
               the Phase 5d exit-wiring lands, advertising restarter
               capability without it would be worse than no GR.";
          }
        }

        leaf multi-topology {
          ext:help "Multi-Topology routing (RFC 5120)";
          // RFC 5120 M-ISIS Multi Topology (MT). IPv6 unicast is the
          // only option used in the industry today, so the enum
          // carries just that one value.
          type enumeration {
            enum ipv6-unicast;   // MT 2 — IPv6 unicast
          }
        }

        list afi-safi {
          ext:help "Per-address-family networks and redistribution";
          // Configured-network advertisement, BGP-style.
          // Each `network` entry under afi-safi=ipv4|ipv6 is emitted in
          // every self-originated LSP as an IP-reach TLV (135 / 236 /
          // 237 depending on MT). Prefix family must match the
          // afi-safi name; the callback rejects mismatches.
          //
          // A bare `afi-safi <ipv4|ipv6>` carries no state — IS-IS does
          // per-AFI enable per-interface, and this list exists only to
          // hold `network` + `redistribute`. Reject the empty entry so a
          // meaningless line can't be committed.
          ext:non-empty "network or redistribute";
          key "name";
          uses zas:afi-safi-unicast;
          list network {
            ext:help "Prefix to advertise as reachable";
            key "prefix";
            leaf prefix {
              ext:help "Prefix to advertise";
              type inet:ip-prefix;
            }
          }
          container redistribute {
            ext:help "Redistribute routes into IS-IS for this AFI";
            presence "Enable route redistribution into IS-IS for this AFI";
            description
              "Per-source redistribution into the IS-IS RIB. Each
               source is a presence container — there is no instance
               keying (zebra-rs has a single instance per protocol).";
            container connected {
              ext:help "Redistribute connected routes";
              presence "Redistribute connected routes";
              uses isis-redist-common;
            }
            container static {
              ext:help "Redistribute static routes";
              presence "Redistribute static routes";
              uses isis-redist-common;
            }
            container bgp {
              ext:help "Redistribute BGP routes";
              presence "Redistribute BGP routes";
              uses isis-redist-common;
            }
            container ospf {
              ext:help "Redistribute OSPF routes";
              presence "Redistribute OSPF routes";
              uses isis-redist-common;
              uses isis-redist-ospf-match;
            }
          }
        }

        leaf te-router-id {
          ext:help "Traffic-engineering stable Router ID";
          type inet:ipv4-address;
        }

        leaf hostname {
          ext:help "Dynamic hostname advertised in TLV 137 (RFC 5301)";
          type string;
        }

        container area-password {
          ext:help "Level-1 area authentication";
          presence "L1 area-wide IS-IS authentication";
          description
            "Authentication key applied to Level-1 self-originated LSPs
             and SNPs (ISO 10589 §9.5 / RFC 5304 / RFC 5310). Per
             ISO 10589, L1 PDUs use the area-wide authentication string.
             Either `password` (inline / cleartext-friendly) or
             `key-chain` (named RFC 8177 chain under /key-chains)
             may carry the key — when both are set the inline
             password wins so that simple-password operators don't
             accidentally get chain-resolved bytes on the wire.";

          leaf password {
            ext:help "Authentication key (cleartext or HMAC key)";
            type string;
            description
              "Authentication key bytes. Sent cleartext on the wire
               when auth-type is text; used as the HMAC key when md5.";
          }
          leaf key-chain {
            ext:help "Named key-chain reference for auth";
            type string;
            description
              "Reference to a named key-chain under /key-chains.
               Only consulted when `password` is unset. The chain's
               active key supplies auth-type, key-id, and material
               at sign/verify time.";
          }
          leaf auth-type {
            ext:help "Authentication type (text / md5 / hmac-sha)";
            type enumeration {
              enum text;         // ISO 10589 §9.5, TLV-10 auth-type 1
              enum md5;          // RFC 5304, TLV-10 auth-type 54
              enum hmac-sha-1;   // RFC 5310 generic crypto, 20-byte digest
              enum hmac-sha-256; // RFC 5310, 32-byte digest
              enum hmac-sha-384; // RFC 5310, 48-byte digest
              enum hmac-sha-512; // RFC 5310, 64-byte digest
            }
            default text;
          }
          leaf key-id {
            ext:help "Key ID for hmac-sha auth-types";
            type uint16;
            default 1;
            description
              "Key Identifier (RFC 5310 §3.1). Only meaningful for
               the hmac-sha-* auth-types; embedded as the 2-byte
               prefix on the TLV-10 value. Ignored for text and md5.
               Receivers MUST present the same Key ID to verify.";
          }
          leaf send-only {
            ext:help "Sign outbound but accept any inbound";
            type boolean;
            default false;
            description
              "Sign outbound but accept any inbound regardless of
               digest — rollover hatch per RFC 5304 §1.";
          }
        }

        container domain-password {
          ext:help "Level-2 domain authentication";
          presence "L2 domain-wide IS-IS authentication";
          description
            "Authentication key applied to Level-2 self-originated LSPs
             and SNPs. Same shape as area-password but scoped to L2.
             Inline `password` wins over `key-chain` when both are set.";

          leaf password {
            ext:help "Authentication key (cleartext or HMAC key)";
            type string;
          }
          leaf key-chain {
            ext:help "Named key-chain reference for auth";
            type string;
            description
              "Reference to a named key-chain under /key-chains.
               Only consulted when `password` is unset.";
          }
          leaf auth-type {
            ext:help "Authentication type (text / md5 / hmac-sha)";
            type enumeration {
              enum text;
              enum md5;
              enum hmac-sha-1;
              enum hmac-sha-256;
              enum hmac-sha-384;
              enum hmac-sha-512;
            }
            default text;
          }
          leaf key-id {
            ext:help "Key ID for hmac-sha auth-types";
            type uint16;
            default 1;
          }
          leaf send-only {
            ext:help "Sign outbound but accept any inbound";
            type boolean;
            default false;
          }
        }

        container timers {
          ext:help "IS-IS protocol timers";
          // `hold-time` (hyphen) matches the callback registered at
          // `/router/isis/timers/hold-time`; the previous `hold_time`
          // spelling never dispatched (dead leaf).
          leaf hold-time {
            ext:help "Adjacency hold time in seconds";
            type uint16;
          }
          leaf lsp-refresh-interval {
            ext:help "LSP refresh interval in seconds";
            type uint16 {
              range "1..65535";
            }
            units "seconds";
          }
          leaf min-lsp-arrival-time {
            ext:help "Minimum LSP arrival time in ms";
            type uint32 {
              range "1..600000";
            }
            units "milliseconds";
          }
        }

        container spf-interval {
          ext:help "SPF calculation throttle timers";
          leaf initial-wait {
            ext:help "Initial SPF delay in milliseconds";
            type uint32 {
              range "1..120000";
            }
            units "milliseconds";
          }
          leaf secondary-wait {
            ext:help "Secondary SPF delay in milliseconds";
            type uint32 {
              range "1..120000";
            }
            units "milliseconds";
          }
          leaf maximum-wait {
            ext:help "Maximum SPF delay in milliseconds";
            type uint32 {
              range "1..120000";
            }
            units "milliseconds";
          }
        }

        container lsp-gen-interval {
          ext:help "LSP generation throttle timers";
          leaf initial-wait {
            ext:help "Initial LSP generation delay in ms";
            type uint32 {
              range "1..120000";
            }
            units "milliseconds";
          }
          leaf secondary-wait {
            ext:help "Secondary LSP-generation wait (ms)";
            type uint32 {
              range "1..120000";
            }
            units "milliseconds";
          }
          leaf maximum-wait {
            ext:help "Maximum LSP-generation wait (ms)";
            type uint32 {
              range "1..120000";
            }
            units "milliseconds";
          }
        }

        leaf lsp-mtu-size {
          ext:help "Maximum size of generated LSPs";
          type uint16 {
            range "128..16384";
          }
          units "bytes";
          description
            "Originating LSP Buffer Size (ISO 10589 originatingLSPBufferSize,
             advertised as TLV 14 per RFC 1195). Sets the maximum byte length
             of a self-originated LSP PDU; the packer fragments TLVs into
             multiple LSPs so each fragment stays at or below this value.
             Default 1492 matches ISO 10589 and is the value every IS-IS
             peer is required to accept.";
        }

        leaf lsp-mtu {
          ext:help "Maximum LSP size transmitted on an interface";
          type uint16 {
            range "400..9490";
          }
          units "bytes";
          description
            "Maximum byte size of an LSP PDU this router transmits. IS-IS
             LSPs are flooded as a single link-layer frame and are never
             fragmented at the link layer, so when lsp-mtu exceeds an
             interface's MTU an LSP of that size cannot fit on the wire.
             LSPs are then dropped on send for that interface (logged at
             warning level) rather than emitted as an over-sized frame.
             Default 1497.";
        }

        list interface {
          ext:help "Per-interface IS-IS configuration";
          // Last item in "router isis" node.
          ext:sort "-10";
          key "if-name";
          leaf if-name {
            ext:help "Interface name";
            ext:dynamic "rib:interface";
            type string;
          }

          leaf circuit-type {
            ext:help "IS-IS level(s): L1 / L1-2 / L2-only";
            type enumeration {
              enum level-1;
              enum level-1-2;
              enum level-2-only;
            }
          }

          leaf area-proxy {
            ext:help "Area Proxy circuit role (RFC 9666): inside / outside";
            type enumeration {
              enum inside;
              enum outside;
            }
            description
              "Explicit RFC 9666 circuit-role override, meaningful only
               while the instance's area-proxy is enabled. Absent, the
               role is derived per §5.1: a circuit that is not also a
               Level 1 circuit (effective level L2-only) is an Outside
               Circuit. On an Outside Circuit L2 IIHs and SNPs are
               sourced from the Proxy System ID (suppressed until it is
               learned), and inside L2 LSPs are filtered from flooding
               and SNPs. Outside circuits should not be configured to
               run Level 1.";
          }

          leaf network-type {
            ext:help "Media type: LAN or point-to-point";
            type enumeration {
              enum lan;
              enum point-to-point;
            }
          }

          leaf passive {
            ext:help "Passive circuit: advertise prefixes, no adjacency";
            type boolean;
            description
              "Run this interface as a passive IS-IS circuit: its
               IPv4/IPv6 prefixes are still advertised into the LSP,
               but no Hello PDUs are sent or processed, so no
               adjacency forms (not even with this router itself when
               its own Hellos loop back). Typically set on loopbacks
               and stub links. Loopback interfaces are implicitly
               passive even when this leaf is unset.";
          }

          leaf priority {
            ext:help "DIS election priority on LAN circuits";
            type uint8;
          }

          container hello {
            ext:help "IS-IS Hello (IIH) parameters";
            leaf padding {
              ext:help "Pad Hello PDUs to full MTU";
              type enumeration {
                enum always;
                /* enum during-adjacency-only; */
                enum disable;
              }
            }
            leaf padding-size {
              ext:help "Pad Hellos to this on-wire frame length instead of MTU";
              type uint16 {
                range "64..16384";
              }
              units "bytes";
              description
                "On-wire Ethernet frame length Hello padding fills toward,
                 as read from a packet capture: 14-byte Ethernet header +
                 3-byte LLC header + IIH PDU, FCS excluded. Overrides the
                 default full-interface-MTU target, for peers whose
                 configured MTU counts L2 overhead inside the number and
                 who therefore drop full-MTU padded Hellos as giants.
                 Clamped to the interface MTU; a value below the unpadded
                 Hello size simply disables padding growth (the Hello is
                 never truncated). Ignored when padding is disable.";
            }
            leaf interval {
              ext:help "Hello PDU transmit interval (seconds)";
              type uint16 {
                range "1..65535";
              }
              units "seconds";
            }
            leaf multiplier {
              ext:help "Hold-time multiplier (missed Hellos to drop)";
              type uint16 {
                range "2..1000";
              }
            }
          }

          leaf csnp-interval {
            ext:help "CSNP transmit interval (seconds)";
            type uint16 {
              range "1..65535";
            }
            units "seconds";
          }

          leaf psnp-interval {
            ext:help "PSNP transmit interval (seconds)";
            type uint16 {
              range "1..65535";
            }
            units "seconds";
          }

          leaf metric {
            ext:help "IS-IS metric for this interface";
            type uint32;
          }

          container ipv4 {
            ext:help "IPv4 address-family settings";
            leaf enabled {
              ext:help "Enable IPv4 on this interface";
              type boolean;
            }
            container prefix-sid {
              ext:help "IPv4 Prefix-SID for this interface";
              leaf index {
                ext:help "Prefix-SID index (offset into SRGB)";
                type uint32;
              }
              leaf absolute {
                ext:help "Absolute Prefix-SID label value";
                type uint32;
              }
              leaf no-php {
                ext:help "Set P-flag: keep node-SID label (no PHP)";
                type empty;
                description
                  "Set the P (no-PHP) flag (RFC 8667 §2.1.1) on this
                   Prefix-SID. When present, the penultimate hop keeps
                   the node-SID label instead of popping it, so the
                   label arrives at this node intact. Absent (default)
                   leaves PHP in effect.";
              }
            }
            list flex-algo-prefix-sid {
              ext:help "Per-Flex-Algo IPv4 Prefix-SID";
              // Per-Flex-Algorithm Prefix-SID for the IPv4 address(es)
              // of this interface. Advertised as additional Prefix-SID
              // sub-TLVs (RFC 8667) with the Algorithm field set to
              // `algo` (RFC 9350 §7), alongside the algo-0 SID in the
              // `prefix-sid` container above. Typically attached to a
              // loopback so the SID identifies this node in the
              // flex-algo's topology.
              key "algo";
              leaf algo {
                ext:help "Flex-Algorithm identifier (128-255)";
                type uint8 { range "128..255"; }
              }
              leaf index {
                ext:help "Prefix-SID index (offset into SRGB)";
                type uint32;
              }
              leaf absolute {
                ext:help "Absolute Prefix-SID label value";
                type uint32;
              }
            }
          }
          container ipv6 {
            ext:help "IPv6 address-family settings";
            leaf enabled {
              ext:help "Enable IPv6 on this interface";
              type boolean;
            }
          }
          list multi-topology {
            ext:help "Per-topology metric override for this link";
            // Per-link, per-MT metric override. Absence falls back to
            // the link's `metric` leaf above.
            key "id";
            leaf id {
              ext:help "Topology (standard or ipv6-unicast)";
              type enumeration {
                enum standard;
                enum ipv6-unicast;
              }
            }
            leaf metric {
              ext:help "Per-topology metric for this link";
              type uint32;
            }
          }

          container hello-authentication {
            ext:help "Hello/CSNP/PSNP authentication";
            presence "Per-interface IIH/CSNP/PSNP authentication";
            description
              "Authentication key applied to IS-IS Hello (IIH), CSNP,
               and PSNP PDUs sent and received on this interface. RFC
               5304 §2 carries this in the TLV-10 Authentication
               Information TLV with auth-type 1 (text) or 54 (md5).
               Per RFC 5304 §1, send-only enables an asymmetric
               rollover where outbound is signed but inbound is
               accepted unconditionally. Inline `password` wins over
               `key-chain` when both are set.";

            leaf password {
              ext:help "Inline authentication key";
              type string;
            }
            leaf key-chain {
              ext:help "Named key-chain (used when password unset)";
              type string;
              description
                "Reference to a named key-chain under /key-chains.
                 Only consulted when `password` is unset.";
            }
            leaf auth-type {
              ext:help "Authentication algorithm (text/md5/hmac-sha)";
              type enumeration {
                enum text;
                enum md5;
                enum hmac-sha-1;
                enum hmac-sha-256;
                enum hmac-sha-384;
                enum hmac-sha-512;
              }
              default text;
            }
            leaf key-id {
              ext:help "Key identifier for hmac-sha auth-types";
              type uint16;
              default 1;
            }
            leaf send-only {
              ext:help "Sign outbound, accept any inbound (rollover)";
              type boolean;
              default false;
            }
          }

          container bfd {
            ext:help "BFD attachment for this IS-IS interface";
            description
              "Per-interface BFD attachment for IS-IS. When `enabled`
               is true the IS-IS adjacency FSM subscribes a BFD
               session at the moment it reaches Up; a subsequent
               BFD Down event drives the adjacency back to Down
               per RFC 5882 §5. Storage-only in PR 6; PR 7 wires
               the runtime subscribe / teardown calls.";

            leaf enabled {
              ext:help "Enable BFD on this interface";
              type boolean;
              default false;
              description
                "Activates the BFD session for adjacencies on this
                 interface. Disabling (or removing the `bfd` block)
                 detaches the session.";
            }

            leaf echo-mode {
              ext:help "BFD Echo role (transmit | receive | both)";
              type enumeration {
                enum transmit { description "Originate Echo only."; }
                enum receive { description "Advertise + reflect only."; }
                enum both { description "Both."; }
              }
              description
                "Enable the BFD Echo function (RFC 5880 §6.4) on this
                 interface's single-hop adjacencies (IPv4, or IPv6 over
                 the link-local pair), choosing which half is active.
                 Backed by the eBPF data plane (system ebpf enabled).
                 Overrides the instance default; absent ⇒ inherit.";
            }
            leaf echo-transmit-interval {
              ext:help "Echo transmit interval (ms)";
              type uint32;
              units "milliseconds";
              description
                "Rate we originate Echo at (echo-mode `transmit`/`both`).
                 Hard default 50 ms when unset at every level.";
            }
            leaf echo-receive-interval {
              ext:help "Advertised Required Min Echo RX Interval (ms)";
              type uint32;
              units "milliseconds";
              description
                "Advertised Required Min Echo RX (echo-mode
                 `receive`/`both`). Hard default 50 ms when unset.";
            }
            leaf detect-offload {
              ext:help "Offload expiration detection to the XDP data plane (kernel)";
              type boolean;
              description
                "Once the session is Up, detect missing BFD control
                 packets in the kernel: the XDP/eBPF data plane
                 re-arms a per-session timer on every arriving control
                 packet (UDP/3784, TTL 255) and drives the session Down
                 with Control Detection Time Expired when they stop
                 (RFC 5880 §6.8.4) — immune to daemon scheduling latency.
                 The userspace detection timer stays armed as a stretched
                 backstop. Overrides the instance default; absent ⇒
                 inherit (false: detection in userspace).";
            }
          }

          container te-metric {
            ext:help "Static TE link metrics (RFC 8570) for this interface";
            description
              "Per-interface traffic-engineering link metrics advertised
               as RFC 8570 sub-TLVs on this link's Extended IS
               Reachability entry (TLV 22, and the MT IS Reach TLV 222
               when multi-topology is enabled). Statically configured
               here; a future performance-measurement (TWAMP/STAMP) task
               will populate the same fields dynamically. All delay
               values are in microseconds.";

            leaf unidirectional-delay {
              ext:help "Average one-way link delay (us)";
              type uint32 {
                range "0..16777215";
              }
              units "microseconds";
              description
                "Average unidirectional link delay (RFC 8570 §4.1,
                 sub-TLV 33).";
            }
            leaf min-delay {
              ext:help "Minimum one-way link delay (us)";
              type uint32 {
                range "0..16777215";
              }
              units "microseconds";
              description
                "Minimum unidirectional link delay (RFC 8570 §4.2,
                 sub-TLV 34). Advertised with max-delay; the Min/Max
                 sub-TLV is emitted only when both are set.";
            }
            leaf max-delay {
              ext:help "Maximum one-way link delay (us)";
              type uint32 {
                range "0..16777215";
              }
              units "microseconds";
              description
                "Maximum unidirectional link delay (RFC 8570 §4.2,
                 sub-TLV 34).";
            }
            leaf delay-variation {
              ext:help "One-way delay variation / jitter (us)";
              type uint32 {
                range "0..16777215";
              }
              units "microseconds";
              description
                "Unidirectional delay variation / jitter (RFC 8570
                 §4.3, sub-TLV 35).";
            }
            leaf loss {
              ext:help "Unidirectional link loss ratio";
              type uint32 {
                range "0..16777214";
              }
              description
                "Unidirectional link loss (RFC 8570 §4.4, sub-TLV 36),
                 encoded in units of 0.000003 %; the maximum 16777214
                 (0xFFFFFE) is ~50.33 %.";
            }
            container measurement {
              ext:help "Measure this link's delay and loss dynamically (STAMP, RFC 8762)";
              description
                "Active performance measurement of this link. When
                 enabled, a STAMP Session-Sender (RFC 8762,
                 unauthenticated) probes the P2P neighbor once the
                 adjacency is up; the damped min/max/avg delay and
                 delay variation populate the same te-metric fields as
                 static configuration (a static leaf, when set,
                 overrides the measured value per field). The probes
                 are answered by the neighbor's implicit
                 Session-Reflector, so measurement must be enabled on
                 both ends of the link.";
              leaf enabled {
                ext:help "Activate delay measurement on this link";
                type boolean;
                description "Activate measurement on this interface.";
              }
              leaf interval {
                ext:help "STAMP probe transmit interval (ms)";
                type uint32 {
                  range "100..60000";
                }
                units "milliseconds";
                description "Probe transmit interval. Default 1000 ms.";
              }
              leaf damping-period {
                ext:help "Minimum spacing between IGP exports (s)";
                type uint32 {
                  range "1..3600";
                }
                units "seconds";
                description
                  "Minimum spacing between exports to the IGP; each
                   period's samples form the advertised min/max/avg
                   window. Default 30 s.";
              }
              leaf anomaly-threshold {
                ext:help "Average delay at/above which the Anomalous bit is set (us)";
                type uint32 {
                  range "0..16777215";
                }
                units "microseconds";
                description
                  "Upper bound for the measured average one-way delay. At or
                   above it, the Anomalous (A) bit is set on the delay
                   sub-TLVs this link advertises (RFC 8570 §4.1 and §4.2), telling
                   receivers the link has degraded past what the operator
                   accepts. Only measured values carry the bit: a delay
                   pinned by the sibling static leaves is always advertised
                   with it clear. Unset disables anomaly detection.";
              }
              leaf reuse-threshold {
                ext:help "Average delay below which the Anomalous bit clears (us)";
                type uint32 {
                  range "0..16777215";
                }
                units "microseconds";
                description
                  "Lower bound at which a set Anomalous bit clears again.
                   Between this and anomaly-threshold the bit holds its
                   current state, so a link resting on the bound does not
                   re-originate every export period. Values above
                   anomaly-threshold are clamped to it. Unset means no
                   hysteresis band: anomaly-threshold both sets and clears.";
              }
              leaf reflector {
                ext:help "How this router reflects the peer's probes (default stateless)";
                type enumeration {
                  enum stateless;
                  enum stateful;
                }
                description
                  "stateless (the default, RFC 8762 section 4.3): replies copy the
                   sender's sequence number. stateful: replies carry this router's own
                   per-peer sequence counter, which lets a peer that declares
                   'loss peer-reflector stateful' tell forward loss from reverse. On if
                   any IGP measuring this link sets it.";
              }
              container loss {
                ext:help "Measured link loss (RFC 8570 / RFC 7471 section 4.4)";
                description
                  "Round-trip probe loss, measured on the same STAMP session
                   and advertised as the unidirectional link-loss sub-TLV. On
                   by default wherever measurement is enabled. Loss runs on
                   its own 30 s bucket clock, independent of damping-period. A
                   static te-metric loss, when set, overrides the measured
                   value.";
                leaf enabled {
                  ext:help "Advertise measured loss (default true)";
                  type boolean;
                  description "Advertise measured loss. Default true.";
                }
                leaf interval {
                  ext:help "Loss averaging and advertisement interval (s, multiple of 30)";
                  type uint32 {
                    range "30..3600";
                  }
                  units "seconds";
                  description
                    "Loss is averaged over the last interval, and re-advertised
                     at most once per interval. Must be a multiple of 30.
                     Default 120 s.";
                }
                leaf threshold {
                  ext:help "Re-advertise on a change of this percent of the advertised value";
                  type uint32 {
                    range "0..100";
                  }
                  units "percent";
                  description
                    "A periodic re-advertisement needs a change of at least this
                     percentage of the advertised value, and at least
                     minimum-change. Default 10.";
                }
                leaf minimum-change {
                  ext:help "Re-advertise only on a change of at least this many percentage points";
                  type decimal64 {
                    fraction-digits 6;
                  }
                  units "percent";
                  description
                    "The smallest absolute change, in percentage points, that is
                     re-advertised. It also governs changes to and from zero.
                     At the default probe rate one lost probe is 0.83 %, so a
                     smaller value lets single-probe noise re-flood. Default 1.0.";
                }
                leaf accelerated-threshold {
                  ext:help "Advertise at once when the latest 30 s differs by this many points";
                  type decimal64 {
                    fraction-digits 6;
                  }
                  units "percent";
                  description
                    "When the latest 30 s bucket alone differs from the
                     advertised value by at least this many percentage points,
                     advertise that value at once instead of waiting for the
                     interval. Unset (the default) disables acceleration.";
                }
                leaf integrity {
                  ext:help "Minimum percent of expected probes for a window to be trusted";
                  type uint32 {
                    range "1..100";
                  }
                  units "percent";
                  description
                    "A loss window is advertised only when at least this
                     percentage of the probes the probe interval should have
                     produced actually settled. Default 90.";
                }
                leaf anomaly-threshold {
                  ext:help "Set the Anomalous bit at or above this loss (percent)";
                  type decimal64 {
                    fraction-digits 6;
                  }
                  units "percent";
                  description
                    "Loss, in percent, at or above which the link-loss sub-TLV's
                     Anomalous (A) bit is set, evaluated on the value it is advertised
                     with (RFC 8570 / RFC 7471 section 4.4). Unset (the default) never
                     sets the bit.";
                }
                leaf reuse-threshold {
                  ext:help "Clear the Anomalous bit after a loss interval below this loss (percent)";
                  type decimal64 {
                    fraction-digits 6;
                  }
                  units "percent";
                  description
                    "Loss, in percent, below which the Anomalous bit clears once the
                     loss has stayed below it for a whole loss interval. Defaults to,
                     and is capped at, anomaly-threshold.";
                }
                leaf peer-reflector {
                  ext:help "How the peer reflects this router's probes (default stateless)";
                  type enumeration {
                    enum stateless;
                    enum stateful;
                  }
                  description
                    "Declares the peer's reflector mode; it cannot be detected.
                     stateless (the default): the advertised loss is round-trip, an upper
                     bound on forward loss. stateful: the peer reflects with its own
                     sequence counter (a zebra-rs peer with 'measurement reflector
                     stateful', a Juniper peer with stateful-sequence), losses are split
                     by direction, and forward loss is advertised. Declaring a stateless
                     peer stateful makes every loss read as reverse.";
                }
              }
            }
          }

          leaf-list affinity {
            ext:help "Affinity-map (admin-group) memberships";
            // Names of /router/isis/affinity-map entries this link
            // belongs to. The union of their bit-positions forms the
            // 256-bit Extended Admin Group bitmap (RFC 7308)
            // advertised for this link inside the ASLA sub-TLV
            // (RFC 9479) whenever at least one flex-algo references
            // an attribute. Held as a plain string (not a leafref)
            // so the per-interface config can be staged before the
            // matching `affinity-map` entry is committed — matches
            // the staging pattern of `srlg` directly below.
            type string;
          }

          leaf-list srlg {
            ext:help "SRLG group memberships for this link";
            // Names of SRLG groups this link is a member of. Each name
            // references a /router/isis/srlg/group entry; the
            // name->value mapping (uint32s advertised in the IS-IS
            // top-level Shared Risk Link Group TLVs — TLV 138 for
            // IPv4, RFC 5307; TLV 139 for IPv6, RFC 6119) is resolved
            // against the IS-IS SRLG table at LSP-build time. Held as
            // a plain string (not a leafref) so the per-interface
            // config can be staged before the matching
            // /router/isis/srlg/group entry is committed — matches
            // the pattern used by segment-routing `block` and
            // `locator` references above.
            type string;
          }
        }

        list vrf {
          ext:help "Per-VRF IS-IS instance";
          // Per-VRF IS-IS instance. Mirrors the (default) top-level
          // IS-IS config tree for each named VRF: the default
          // `router isis` task forwards every `vrf <name> ...` line —
          // with the `vrf <name>` prefix stripped — to a full per-VRF
          // IS-IS instance whose computed routes install into the
          // VRF's routing table. The `vrf` key is a plain string
          // (staging-friendly, like `router static`'s per-VRF list)
          // so the VRF need not yet exist at the top-level `vrf` list
          // when this config is parsed. Exposed subset: net / is-type,
          // the instance + per-interface timers, and afi-safi network
          // / redistribution; more leaves land as the per-VRF surface
          // widens toward full parity with the default instance.
          key "name";
          leaf name {
            ext:help "VRF name";
            ext:dynamic "rib:vrf";
            type string;
          }
          leaf net {
            ext:help "Network Entity Title (area + system-id)";
            // First entry in "router isis vrf X" node (mirrors the
            // top-level `net` sort) so forwarded config arrives
            // system-id-first.
            ext:sort "1";
            type isis:net;
          }
          leaf is-type {
            ext:help "IS-IS level for this VRF (L1 / L1-2 / L2-only)";
            type enumeration {
              enum level-1;
              enum level-1-2;
              enum level-2-only;
            }
          }
          leaf te-router-id {
            ext:help "Traffic-engineering stable Router ID";
            // Forwarded to the child's `/router/isis/te-router-id`
            // callback and stored per-VRF. NOTE: the TLVs that carry
            // it (TE Router ID 134, Router Capability router-id) are
            // gated on `sr_enabled()` at LSP build time, and the
            // per-VRF surface doesn't expose `segment-routing` yet —
            // so the value stages today and goes on the wire once
            // per-VRF SR lands.
            type inet:ipv4-address;
          }
          container timers {
            ext:help "IS-IS protocol timers";
            // `hold-time` (hyphen) matches the callback path
            // `/router/isis/timers/hold-time`. (The top-level leaf is
            // also `hold-time`.)
            leaf hold-time {
              ext:help "Adjacency hold time and LSP lifetime (seconds)";
              type uint16;
            }
            leaf lsp-refresh-interval {
              ext:help "LSP refresh interval (seconds)";
              type uint16 {
                range "1..65535";
              }
              units "seconds";
            }
            leaf min-lsp-arrival-time {
              ext:help "Minimum LSP arrival spacing (ms)";
              type uint32 {
                range "1..600000";
              }
              units "milliseconds";
            }
          }
          container spf-interval {
            ext:help "SPF calculation throttle timers";
            leaf initial-wait {
              ext:help "Initial SPF delay (ms)";
              type uint32 {
                range "1..120000";
              }
              units "milliseconds";
            }
            leaf secondary-wait {
              ext:help "Secondary SPF wait (ms)";
              type uint32 {
                range "1..120000";
              }
              units "milliseconds";
            }
            leaf maximum-wait {
              ext:help "Maximum SPF wait (ms)";
              type uint32 {
                range "1..120000";
              }
              units "milliseconds";
            }
          }
          container lsp-gen-interval {
            ext:help "LSP generation throttle timers";
            leaf initial-wait {
              ext:help "Initial LSP-generation delay (ms)";
              type uint32 {
                range "1..120000";
              }
              units "milliseconds";
            }
            leaf secondary-wait {
              ext:help "Secondary LSP-generation wait (ms)";
              type uint32 {
                range "1..120000";
              }
              units "milliseconds";
            }
            leaf maximum-wait {
              ext:help "Maximum LSP-generation wait (ms)";
              type uint32 {
                range "1..120000";
              }
              units "milliseconds";
            }
          }
          list afi-safi {
            ext:help "Per-AFI networks and redistribution";
            // Per-AFI self-originated networks + redistribution
            // (mirrors the default instance, reusing the same
            // groupings). Forwarded `/router/isis/afi-safi/...` paths
            // match the existing v2 callbacks.
            ext:non-empty "network or redistribute";
            key "name";
            uses zas:afi-safi-unicast;
            list network {
              ext:help "Network advertised into IS-IS";
              key "prefix";
              leaf prefix {
                ext:help "Prefix to advertise";
                type inet:ip-prefix;
              }
            }
            container redistribute {
              ext:help "Redistribute routes into IS-IS";
              presence "Enable route redistribution into IS-IS for this AFI";
              container connected {
                ext:help "Redistribute connected routes";
                presence "Redistribute connected routes";
                uses isis-redist-common;
              }
              container static {
                ext:help "Redistribute static routes";
                presence "Redistribute static routes";
                uses isis-redist-common;
              }
              container bgp {
                ext:help "Redistribute BGP routes";
                presence "Redistribute BGP routes";
                uses isis-redist-common;
              }
              container ospf {
                ext:help "Redistribute OSPF routes";
                presence "Redistribute OSPF routes";
                uses isis-redist-common;
                uses isis-redist-ospf-match;
              }
            }
          }
          list interface {
            ext:help "Per-interface IS-IS configuration";
            // Last item, mirroring the top-level interface sort.
            ext:sort "-10";
            key "if-name";
            leaf if-name {
              ext:help "Interface name";
              ext:dynamic "rib:interface";
              type string;
            }
            leaf circuit-type {
              ext:help "IS-IS level(s): L1 / L1-2 / L2-only";
              type enumeration {
                enum level-1;
                enum level-1-2;
                enum level-2-only;
              }
            }
            leaf network-type {
              ext:help "Media type: LAN or point-to-point";
              type enumeration {
                enum lan;
                enum point-to-point;
              }
            }
            leaf passive {
              ext:help "Passive circuit: advertise prefixes, no adjacency";
              type boolean;
              description
                "Passive IS-IS circuit: advertise the interface's
                 prefixes but send/process no Hello PDUs (no
                 adjacency). See the top-level interface's `passive`
                 leaf.";
            }
            leaf priority {
              ext:help "DIS election priority on LAN circuits";
              type uint8;
            }
            container hello {
              ext:help "IS-IS Hello (IIH) parameters";
              leaf padding {
                ext:help "Pad Hello PDUs to full MTU";
                type enumeration {
                  enum always;
                  enum disable;
                }
              }
              leaf padding-size {
                ext:help "Pad Hellos to this on-wire frame length instead of MTU";
                type uint16 {
                  range "64..16384";
                }
                units "bytes";
                description
                  "On-wire Ethernet frame length Hello padding fills toward,
                   as read from a packet capture: 14-byte Ethernet header +
                   3-byte LLC header + IIH PDU, FCS excluded. Overrides the
                   default full-interface-MTU target, for peers whose
                   configured MTU counts L2 overhead inside the number and
                   who therefore drop full-MTU padded Hellos as giants.
                   Clamped to the interface MTU; a value below the unpadded
                   Hello size simply disables padding growth (the Hello is
                   never truncated). Ignored when padding is disable.";
              }
              leaf interval {
                ext:help "Hello PDU transmit interval (seconds)";
                type uint16 {
                  range "1..65535";
                }
                units "seconds";
              }
              leaf multiplier {
                ext:help "Hold-time multiplier (missed Hellos to drop)";
                type uint16 {
                  range "2..1000";
                }
              }
            }
            leaf csnp-interval {
              ext:help "CSNP transmit interval (seconds)";
              type uint16 {
                range "1..65535";
              }
              units "seconds";
            }
            leaf psnp-interval {
              ext:help "PSNP transmit interval (seconds)";
              type uint16 {
                range "1..65535";
              }
              units "seconds";
            }
            leaf metric {
              ext:help "IS-IS metric for this interface";
              type uint32;
            }
            container ipv4 {
              ext:help "IPv4 address-family settings";
              leaf enabled {
                ext:help "Enable IPv4 on this interface";
                type boolean;
              }
            }
            container ipv6 {
              ext:help "IPv6 address-family settings";
              leaf enabled {
                ext:help "Enable IPv6 on this interface";
                type boolean;
              }
            }
          }
        }
      }
      container pim {
        ext:help "PIM-SM routing protocol configuration";
        presence "Enables configuration of PIM-SM";
        container bsr {
          ext:help "Bootstrap Router (RFC 5059)";
          container candidate-bsr {
            ext:help "Run as a candidate Bootstrap Router";
            presence "Candidate BSR";
            leaf address {
              ext:help "Advertised BSR address (one of this router's addresses)";
              type inet:ipv4-address;
            }
            leaf priority {
              ext:help "BSR election priority (higher wins)";
              type uint8;
              default 64;
            }
          }
          container candidate-rp {
            ext:help "Advertise this router as a candidate RP";
            presence "Candidate RP";
            leaf address {
              ext:help "Advertised RP address (one of this router's addresses)";
              type inet:ipv4-address;
            }
            leaf group {
              ext:help "Group prefix this RP serves";
              type inet:ipv4-prefix;
              default "224.0.0.0/4";
            }
            leaf priority {
              ext:help "Candidate RP priority (lower preferred)";
              type uint8;
              default 192;
            }
          }
        }
        container rp {
          ext:help "Rendezvous Point configuration";
          list static {
            ext:help "Static RP address for a group range";
            key "address";
            leaf address {
              ext:help "RP address";
              type inet:ipv4-address;
            }
            leaf group {
              ext:help "Multicast group prefix served by this RP";
              type inet:ipv4-prefix;
              default "224.0.0.0/4";
            }
          }
        }
        list interface {
          ext:help "Per-interface PIM configuration";
          key "if-name";
          leaf if-name {
            ext:help "Interface name";
            ext:dynamic "rib:interface";
            type string;
          }
          leaf enabled {
            ext:help "Enable PIM on this interface";
            type boolean;
            default false;
          }
          leaf dr-priority {
            ext:help "Designated Router election priority";
            type uint32;
            default 1;
          }
          container hello {
            ext:help "PIM Hello parameters";
            leaf interval {
              ext:help "Hello transmit interval (seconds)";
              type uint16 {
                range "1..18000";
              }
              units "seconds";
              default 30;
            }
            leaf holdtime {
              ext:help "Neighbor holdtime advertised in Hellos (seconds)";
              type uint16 {
                range "1..65535";
              }
              units "seconds";
            }
          }
          // Loopbacks are implicitly passive even when unset.
          leaf passive {
            ext:help "Do not send or process PIM packets on this interface";
            type boolean;
            default false;
          }
          container igmp {
            ext:help "IGMP on this interface";
            leaf enabled {
              ext:help "Enable IGMP membership tracking";
              type boolean;
              default false;
            }
            leaf version {
              ext:help "IGMP version to run";
              type uint8 {
                range "2..3";
              }
              default 3;
            }
            leaf query-interval {
              ext:help "General query transmit interval (seconds)";
              type uint16 {
                range "1..1800";
              }
              units "seconds";
              default 125;
            }
            leaf query-max-response-time {
              ext:help "Max response time advertised in queries (seconds)";
              type uint16 {
                range "1..25";
              }
              units "seconds";
              default 10;
            }
          }
        }
        container ipv6 {
          ext:help "PIMv6 (IPv6) configuration";
          // The default `router pim` task forwards every `ipv6 ...`
          // line — with the `ipv6` container stripped — to a
          // default-table Pim<Ipv6> instance whose PIMv6 socket runs
          // over link-local transport.
          container rp {
            ext:help "Rendezvous Point configuration";
            list static {
              ext:help "Static RP address for a group range";
              key "address";
              leaf address {
                ext:help "RP address";
                type inet:ipv6-address;
              }
              leaf group {
                ext:help "Multicast group prefix served by this RP";
                type inet:ipv6-prefix;
                default "ff00::/8";
              }
            }
          }
          container bsr {
            ext:help "Bootstrap Router (RFC 5059)";
            container candidate-bsr {
              ext:help "Run as a candidate Bootstrap Router";
              presence "Candidate BSR";
              leaf address {
                ext:help "Advertised BSR address (one of this router's addresses)";
                type inet:ipv6-address;
              }
              leaf priority {
                ext:help "BSR election priority (higher wins)";
                type uint8;
                default 64;
              }
            }
            container candidate-rp {
              ext:help "Advertise this router as a candidate RP";
              presence "Candidate RP";
              leaf address {
                ext:help "Advertised RP address (one of this router's addresses)";
                type inet:ipv6-address;
              }
              leaf group {
                ext:help "Group prefix this RP serves";
                type inet:ipv6-prefix;
                default "ff00::/8";
              }
              leaf priority {
                ext:help "Candidate RP priority (lower preferred)";
                type uint8;
                default 192;
              }
            }
          }
          list interface {
            ext:help "Per-interface PIMv6 configuration";
            key "if-name";
            leaf if-name {
              ext:help "Interface name";
              ext:dynamic "rib:interface";
              type string;
            }
            leaf enabled {
              ext:help "Enable PIM on this interface";
              type boolean;
              default false;
            }
            leaf dr-priority {
              ext:help "Designated Router election priority";
              type uint32;
              default 1;
            }
            container hello {
              ext:help "PIM Hello parameters";
              leaf interval {
                ext:help "Hello transmit interval (seconds)";
                type uint16 {
                  range "1..18000";
                }
                units "seconds";
                default 30;
              }
              leaf holdtime {
                ext:help "Neighbor holdtime advertised in Hellos (seconds)";
                type uint16 {
                  range "1..65535";
                }
                units "seconds";
              }
            }
            // Loopbacks are implicitly passive even when unset.
            leaf passive {
              ext:help "Do not send or process PIM packets on this interface";
              type boolean;
              default false;
            }
            container mld {
              ext:help "MLD on this interface";
              leaf enabled {
                ext:help "Enable MLD membership tracking";
                type boolean;
                default false;
              }
              leaf version {
                ext:help "MLD version to run";
                type uint8 {
                  range "1..2";
                }
                default 2;
              }
              leaf query-interval {
                ext:help "General query transmit interval (seconds)";
                type uint16 {
                  range "1..1800";
                }
                units "seconds";
                default 125;
              }
              leaf query-max-response-time {
                ext:help "Max response time advertised in queries (seconds)";
                type uint16 {
                  range "1..25";
                }
                units "seconds";
                default 10;
              }
            }
          }
        }
        list vrf {
          ext:help "Per-VRF PIM instance";
          // Mirrors the default PIM tree for each named VRF: the
          // default `router pim` task forwards every `vrf <name> ...`
          // line — with the `vrf <name>` prefix stripped — to a full
          // per-VRF PIM instance whose sockets and kernel MFC live in
          // the VRF (SO_BINDTODEVICE + MRT_TABLE). Hand-declared
          // subset, like `router isis`'s vrf list.
          key "name";
          leaf name {
            ext:help "VRF name";
            ext:dynamic "rib:vrf";
            type string;
          }
          container rp {
            ext:help "Rendezvous Point configuration";
            list static {
              ext:help "Static RP address for a group range";
              key "address";
              leaf address {
                ext:help "RP address";
                type inet:ipv4-address;
              }
              leaf group {
                ext:help "Multicast group prefix served by this RP";
                type inet:ipv4-prefix;
                default "224.0.0.0/4";
              }
            }
          }
          list interface {
            ext:help "Per-interface PIM configuration";
            key "if-name";
            leaf if-name {
              ext:help "Interface name";
              ext:dynamic "rib:interface";
              type string;
            }
            leaf enabled {
              ext:help "Enable PIM on this interface";
              type boolean;
              default false;
            }
            leaf dr-priority {
              ext:help "Designated Router election priority";
              type uint32;
              default 1;
            }
            container hello {
              ext:help "PIM Hello parameters";
              leaf interval {
                ext:help "Hello transmit interval (seconds)";
                type uint16 {
                  range "1..18000";
                }
                units "seconds";
                default 30;
              }
              leaf holdtime {
                ext:help "Neighbor holdtime advertised in Hellos (seconds)";
                type uint16 {
                  range "1..65535";
                }
                units "seconds";
              }
            }
            // Loopbacks are implicitly passive even when unset.
            leaf passive {
              ext:help "Do not send or process PIM packets on this interface";
              type boolean;
              default false;
            }
            container igmp {
              ext:help "IGMP on this interface";
              leaf enabled {
                ext:help "Enable IGMP membership tracking";
                type boolean;
                default false;
              }
              leaf version {
                ext:help "IGMP version to run";
                type uint8 {
                  range "2..3";
                }
                default 3;
              }
              leaf query-interval {
                ext:help "General query transmit interval (seconds)";
                type uint16 {
                  range "1..1800";
                }
                units "seconds";
                default 125;
              }
              leaf query-max-response-time {
                ext:help "Max response time advertised in queries (seconds)";
                type uint16 {
                  range "1..25";
                }
                units "seconds";
                default 10;
              }
            }
          }
          container ipv6 {
            ext:help "PIMv6 (IPv6) configuration in this VRF";
            // The per-VRF `Pim<Ipv4>` child strips the `ipv6` container
            // and forwards to a per-VRF `Pim<Ipv6>` grandchild scoped to
            // the same table.
            container rp {
              ext:help "Rendezvous Point configuration";
              list static {
                ext:help "Static RP address for a group range";
                key "address";
                leaf address {
                  ext:help "RP address";
                  type inet:ipv6-address;
                }
                leaf group {
                  ext:help "Multicast group prefix served by this RP";
                  type inet:ipv6-prefix;
                  default "ff00::/8";
                }
              }
            }
            list interface {
              ext:help "Per-interface PIMv6 configuration";
              key "if-name";
              leaf if-name {
                ext:help "Interface name";
                ext:dynamic "rib:interface";
                type string;
              }
              leaf enabled {
                ext:help "Enable PIM on this interface";
                type boolean;
                default false;
              }
              leaf dr-priority {
                ext:help "Designated Router election priority";
                type uint32;
                default 1;
              }
              container hello {
                ext:help "PIM Hello parameters";
                leaf interval {
                  ext:help "Hello transmit interval (seconds)";
                  type uint16 {
                    range "1..18000";
                  }
                  units "seconds";
                  default 30;
                }
                leaf holdtime {
                  ext:help "Neighbor holdtime advertised in Hellos (seconds)";
                  type uint16 {
                    range "1..65535";
                  }
                  units "seconds";
                }
              }
              // Loopbacks are implicitly passive even when unset.
              leaf passive {
                ext:help "Do not send or process PIM packets on this interface";
                type boolean;
                default false;
              }
              container mld {
                ext:help "MLD on this interface";
                leaf enabled {
                  ext:help "Enable MLD membership tracking";
                  type boolean;
                  default false;
                }
                leaf version {
                  ext:help "MLD version to run";
                  type uint8 {
                    range "1..2";
                  }
                  default 2;
                }
                leaf query-interval {
                  ext:help "General query transmit interval (seconds)";
                  type uint16 {
                    range "1..1800";
                  }
                  units "seconds";
                  default 125;
                }
                leaf query-max-response-time {
                  ext:help "Max response time advertised in queries (seconds)";
                  type uint16 {
                    range "1..25";
                  }
                  units "seconds";
                  default 10;
                }
              }
            }
          }
        }
      }
      container static {
        ext:help "Static route configuration";

        // Default / global instance — no `vrf` key. The on-the-wire
        // paths under `router/static/{ipv4,ipv6,mpls}` are unchanged
        // from before the extraction, so existing callbacks keep
        // their registrations.
        uses static:static-routes;

        // Per-VRF instance. The same static-routes shape is reused
        // for each named VRF; routes configured here install into
        // the VRF's routing table once VRF support is wired into
        // the FIB. The `vrf` key is a plain string (matches the
        // staging-friendly pattern used by IS-IS for `block` and
        // `locator`) — the VRF need not yet be declared at the
        // top-level `vrf` list when this config is parsed.
        list vrf {
          ext:help "Per-VRF static route configuration";
          key "name";
          description
            "Per-VRF static-routing tree. All address families allowed
             at the global level are also allowed here.";
          leaf name {
            ext:help "VRF name";
            type string;
            description
              "Name of the VRF this static block applies to. Matches
               the key of the top-level `vrf` list.";
          }
          uses static:static-routes;
        }
      }
    }

    // BFD has no top-level config: it is configured per-protocol
    // (`neighbor X bfd`, `ip ospf bfd`, `isis bfd`) and the BFD task is
    // spawned eagerly the first time one of those protocols comes up
    // (see `config/manager.rs`).

    container segment-routing {
      ext:help "Segment Routing global configuration";
      description
        "Global Segment Routing configuration shared across protocols.
         Blocks (SR-MPLS label ranges) and locators (SRv6 SID prefixes)
         defined here can be referenced by name from the per-protocol
         segment-routing sections (e.g. router/isis/segment-routing/mpls
         and router/isis/segment-routing/srv6). Managed by the RIB,
         which is the natural owner of the SID/label space and the
         per-block / per-locator install state.";

      list block {
        ext:help "SR-MPLS label block (SRGB + SRLB)";
        key "name";
        description
          "SR-MPLS label block. Each block bundles an SR Global Block
           (SRGB) and an SR Local Block (SRLB) under one name so multiple
           protocols (IS-IS, OSPF, BGP-LU) can share the same
           configuration by reference.";
        leaf name {
          ext:help "Label block name";
          type string;
        }
        container global {
          ext:help "SR Global Block (SRGB) label range";
          description
            "SR Global Block (SRGB) — prefix-SID label range advertised
             to the SR domain. Matches the IS-IS SR Capability TLV
             (RFC 8667 §3.1) <base-label, range> shape.";
          leaf start {
            ext:help "First label of the SRGB range";
            type uint32;
          }
          leaf range {
            ext:help "Number of labels in the SRGB";
            type uint32;
          }
        }
        container local {
          ext:help "SR Local Block (SRLB) label range";
          description
            "SR Local Block (SRLB) — adjacency-SID label range used
             locally. Same <base-label, range> shape as global.";
          leaf start {
            ext:help "First label of the SRLB range";
            type uint32;
          }
          leaf range {
            ext:help "Number of labels in the SRLB";
            type uint32;
          }
        }
      }

      list locator {
        ext:help "SRv6 locator (SID prefix)";
        key "name";
        description
          "SRv6 locator. The prefix is the IPv6 range from which SIDs
           are allocated; behavior selects the SID layout.";
        leaf name {
          ext:help "Locator name";
          type string;
        }
        leaf prefix {
          ext:help "IPv6 prefix for SID allocation";
          type inet:ipv6-prefix;
          description
            "IPv6 prefix from which SIDs are allocated for this locator.";
        }
        leaf behavior {
          ext:help "SID layout (usid / replace / full)";
          type enumeration {
            enum usid;
            enum replace;
          }
          description
            "Locator-wide endpoint behavior. 'usid' selects the
             RFC 9800 NEXT-C-SID (micro-SID) format; 'replace' the
             RFC 9800 REPLACE-C-SID format (32-bit C-SIDs consumed
             from packed containers, e.g. a /64 locator advertises
             LB 48 / LN 16 / Fun 16 / Arg 48); absent means the
             classic RFC 8986 full-SID layout.";
        }
        leaf vrf {
          ext:help "Bind node SID to this VRF (End.T)";
          type string;
          description
            "Bind the locator's node SID to this VRF's IPv6 table:
             the End SID becomes End.T (RFC 8986 4.3) — or uT when
             the locator behavior is usid — and the End walk's
             egress lookup happens in the VRF's table. Adjacency
             (End.X/uA) SIDs are unaffected. Ignored for behavior
             replace.";
        }
        leaf-list flavor {
          ext:help "Endpoint flavors (psp / usp / usd)";
          type enumeration {
            enum psp;
            enum usp;
            enum usd;
          }
          description
            "RFC 8986 4.16 endpoint flavors applied to the End/uN and
             End.X/uA SIDs allocated from this locator (End.X SIDs take
             only psp — their usp/usd variants are not implemented).
             psp pops the SRH at the penultimate segment, usp pops it
             at the ultimate segment, usd decapsulates there.";
        }
      }

      list replication-segment {
        ext:help "RFC 9524 SR-P2MP replication segment (End.Replicate)";
        key "name";
        description
          "An SRv6 RFC 9524 replication-tree node. 'sid' is the local
           End.Replicate SID; each 'branch' names a downstream
           Replication-SID a received copy is cloned toward. Programmed
           into the cradle eBPF data plane (REPL_SEG) — there is no kernel
           seg6local action for replication.";
        leaf name {
          ext:help "Replication-segment name";
          type string;
        }
        leaf sid {
          ext:help "Local End.Replicate SID";
          type inet:ipv6-address;
          description
            "The replication segment's SID — the arriving outer IPv6
             destination of a copy. Registered as a local End.Replicate
             SID so the data plane fans matching frames out to the
             branches.";
        }
        leaf hop-limit-threshold {
          ext:help "RFC 9524 Hop-Limit threshold (0 = disabled)";
          type uint8;
          description
            "Discard a copy whose arriving IPv6 Hop Limit is below this
             value (RFC 9524 5.2). 0 disables the check.";
        }
        list branch {
          ext:help "Downstream replication branch";
          key "sid";
          description
            "One downstream branch: a received copy is steered to 'sid'
             (a remote leaf's End.DT2M SID, or the next tier's
             End.Replicate SID).";
          leaf sid {
            ext:help "Downstream Replication-SID";
            type inet:ipv6-address;
          }
          leaf nexthop-id {
            ext:help "Explicit underlay nexthop id (0 = FIB6 on the SID)";
            type uint32;
            description
              "Underlay adjacency for this branch. 0 (default) resolves
               it by a FIB6 lookup on the branch SID (the IGP locator
               route), like the EVPN End.DT2M encap.";
          }
        }
      }
    }

    list community-set {
      ext:help "BGP standard community set";
      ext:sort "5";
      key "name";
      leaf name {
        ext:help "Community-set name";
        type string;
      }
      leaf-list members {
        ext:help "Community values in this set";
        type string;
        description
          "Members of the community set";
      }
    }

    list ext-community-set {
      ext:help "BGP extended community set";
      ext:sort "5";
      key "name";
      leaf name {
        ext:help "Ext-community-set name";
        type string;
      }
      leaf-list members {
        ext:help "RT / SoO matchers (rt: / soo:)";
        type string;
        description
          "Ext-community matchers. Each member is one of:
            - `rt:ASN:NN` / `rt:IPv4:NN` (Route Target),
            - `soo:ASN:NN` / `soo:IPv4:NN` (Site-of-Origin),
            - `rt:<regex>` / `soo:<regex>` (regex applied to the
              value portion after the `rt:`/`soo:` prefix).
           Standard-community syntax is rejected here; use
           `community-set` for those.";
      }
    }

    list large-community-set {
      ext:help "BGP large community set";
      ext:sort "5";
      key "name";
      leaf name {
        ext:help "Large-community-set name";
        type string;
      }
      leaf-list members {
        ext:help "Large-community matchers (A:B:C or regex)";
        type string;
        description
          "Large-community matchers. Each member is either an
           exact `A:B:C` triple (three colon-separated uint32s
           per RFC 8092) or a regex applied to the textual
           `A:B:C` form of each LARGE_COMMUNITIES element on
           the route.";
      }
    }

    list as-path-set {
      ext:help "AS-path match set";
      ext:sort "5";
      key "name";
      leaf name {
        ext:help "AS-path set name";
        type string;
      }
      leaf-list members {
        ext:help "AS-path regex matchers";
        type string;
        description
          "Regular expression members matched against the route's
           AS_PATH attribute, rendered as a space-separated list of
           ASNs (e.g. \"65001 65002 65003\"; AS_SET members are
           comma-separated, e.g. \"{65010,65011}\"). Syntax is
           compatible with FRR's `bgp as-path access-list`: the `_`
           magic character expands to (^|[,{}() ]|$), so `_65001_`
           matches AS 65001 anywhere in the path, `^65001_` matches the
           neighbor AS, and `_65001$` matches the origin AS.";
      }
    }

    list prefix-set {
      ext:help "Prefix match set";
      ext:sort "6";
      key "name";
      leaf name {
        ext:help "Prefix-set name";
        type string;
      }
      list "prefixes" {
        ext:help "Prefix entry in the set";
        key "prefix";
        leaf "prefix" {
          ext:help "IPv4/IPv6 prefix to match";
          type union {
            type inet:ipv4-prefix;
            type inet:ipv6-prefix;
          }
        }
        leaf le {
          ext:help "Maximum prefix length to match";
          type uint8;
          description
            "Members of the prefix set";
        }
        leaf eq {
          ext:help "Exact prefix length to match";
          type uint8;
          description
            "Members of the prefix set";
        }
        leaf ge {
          ext:help "Minimum prefix length to match";
          type uint8;
          description
            "Members of the prefix set";
        }
      }
    }
    // VyOS-compatible firewall (see firewall.yang). Part of the
    // insomnia-only config surface: the whole subtree is feature-gated, so
    // it exists only when the daemon runs with `--feature insomnia`.
    container firewall {
      if-feature feat:insomnia;
      ext:help "Firewall configuration";
      uses "fw:firewall";
    }

    // Also insomnia-only: the whole VPN subtree (only IPsec today) exists
    // solely with `--feature insomnia`.
    container vpn {
      if-feature feat:insomnia;
      ext:help "Virtual Private Network (VPN)";
      container ipsec {
        ext:help "VPN IP security (IPsec) parameters";
        uses "ipsec:vpn-ipsec";
      }
    }

    // VyOS-derived VRRP (see vrrp.yang): VyOS's `high-availability`
    // wrapper is dropped, `vrrp` is a top-level node. insomnia-only.
    // The top level is the global table; `vrrp vrf <name> …` is the same
    // tree for a VRF (zebra-rs's `<feature> vrf <name>` convention;
    // VyOS has no per-VRF VRRP). `default` is refused as a name at
    // commit (config::check::reserved_vrf).
    container vrrp {
      if-feature feat:insomnia;
      ext:help "Virtual Router Redundancy Protocol (VRRP)";
      uses "vrrp:vrrp";
      list vrf {
        ext:help "VRRP in a VRF";
        key "name";
        leaf name {
          ext:help "VRF name";
          ext:dynamic "rib:vrf";
          type string;
        }
        uses "vrrp:vrrp";
      }
    }

    // VyOS-derived system services (see dhcp.yang), under VyOS's own
    // `service` node so `set service …` lines port verbatim.
    // insomnia-only. Each DHCP tree is instantiated twice: for the
    // default VRF, and per VRF under `vrf <name>`, zebra-rs's
    // `<feature> vrf <name>` convention (VyOS spells the server's
    // `vrf name <n> service dhcp-server`, and has no per-VRF relay).
    container service {
      if-feature feat:insomnia;
      ext:help "System services";
      container dhcp-server {
        ext:help "Dynamic Host Configuration Protocol (DHCP) for DHCP server";
        uses "dhcp:dhcp-server";
        list vrf {
          ext:help "DHCP server in a VRF";
          key "name";
          leaf name {
            ext:help "VRF name";
            ext:dynamic "rib:vrf";
            type string;
          }
          uses "dhcp:dhcp-server";
        }
      }
      container dhcpv6-server {
        ext:help "DHCP for IPv6 (DHCPv6) server";
        uses "dhcp:dhcpv6-server";
        list vrf {
          ext:help "DHCPv6 server in a VRF";
          key "name";
          leaf name {
            ext:help "VRF name";
            ext:dynamic "rib:vrf";
            type string;
          }
          uses "dhcp:dhcpv6-server";
        }
      }
      container dhcp-relay {
        ext:help "Host Configuration Protocol (DHCP) relay agent";
        uses "dhcp:dhcp-relay";
        list vrf {
          ext:help "DHCP relay agent in a VRF";
          key "name";
          leaf name {
            ext:help "VRF name";
            ext:dynamic "rib:vrf";
            type string;
          }
          uses "dhcp:dhcp-relay";
        }
      }
      container dhcpv6-relay {
        ext:help "DHCPv6 Relay Agent parameters";
        uses "dhcp:dhcpv6-relay";
        list vrf {
          ext:help "DHCPv6 relay agent in a VRF";
          key "name";
          leaf name {
            ext:help "VRF name";
            ext:dynamic "rib:vrf";
            type string;
          }
          uses "dhcp:dhcpv6-relay";
        }
      }
    }

    list interface {
      ext:help "Interface configuration";
      ext:sort "20";
      key "if-name";
      leaf if-name {
        ext:help "Interface name";
        ext:dynamic "rib:interface";
        type string;
      }
      leaf vrf {
        ext:help "Enslave interface to this VRF";
        // Highest priority among interface children so the enslave to
        // the VRF master is applied before any address: the kernel then
        // creates the connected route directly in the VRF table instead
        // of in the default table (which would otherwise have to be
        // moved on bind).
        ext:sort "10";
        ext:dynamic "rib:vrf";
        type leafref {
          path "/vrf/name";
        }
        description
          "Enslave this interface to the named VRF master device.
           Omitted means the interface lives in the default routing
           instance.";
      }
      leaf bridge {
        ext:help "Enslave interface to this bridge";
        // Same priority as `vrf` (and mutually exclusive with it in
        // practice — an interface has a single kernel IFLA_MASTER):
        // apply the enslave before any address.
        ext:sort "11";
        ext:dynamic "rib:bridge";
        type leafref {
          path "/bridge/name";
        }
        description
          "Enslave this interface to the named bridge master device,
           equivalent to `ip link set <if-name> master <bridge>`. The
           bind is staged and applied once both the interface and the
           bridge exist in the kernel, so config order is free (the
           bridge may be created after this leaf is set). Omitted means
           the interface is not a bridge port.";
      }
      leaf mtu {
        ext:help "Maximum transmission unit in bytes";
        type uint32 {
          range "68..65535";
        }
        description
          "Operator-set interface MTU. When unset the interface keeps
           the MTU the kernel assigned it (typically 65536 for loopback,
           1500 otherwise); deleting this leaf restores that originally-
           observed value. The IPv6 minimum is 1280, so setting a smaller
           MTU on an interface with IPv6 enabled is rejected by the
           kernel and reported by `show interface`.";
      }
      // Data-plane port membership for the cradle/eBPF integration:
      // attaches this interface to the eBPF forwarding plane (the XDP
      // and TC programs) once an engine is reachable — spawned via
      // `system ebpf enabled` or external via `system cradle`. The
      // port's VRF binding follows this interface's `vrf` leaf.
      container ebpf {
        ext:help "eBPF data-plane attachment";
        leaf enabled {
          ext:help "Attach this interface to the eBPF data plane";
          type boolean;
          description
            "When true, this interface is programmed as a cradle data-plane
             port: the XDP and TC forwarding programs attach to it and it
             participates in eBPF forwarding. When false or unset the
             interface is detached. Inert unless a cradle engine is
             managed (`system ebpf enabled`) or reachable
             (`system cradle enabled`).";
        }
      }
      container ipv4 {
        ext:help "IPv4 configuration";
        list address {
          ext:help "IPv4 interface address, or dhcp to acquire one";
          key "address";
          ordered-by user;
          must "not(../address[address = 'dhcp']) or count(../address) = 1" {
            error-message
              "address dhcp cannot be combined with a static address";
            description
              "An interface is addressed by DHCP or statically, not
               both. The schema library parses `must` and does not
               evaluate it: the commit check
               `config::check::address_dhcp_exclusive` enforces this.";
          }
          description
            "Interface IPv4 addresses, one entry per address. A keyed
             list and not a leaf-list so that a command names exactly
             one address (`address 10.0.0.1/24`, `address dhcp`): the
             CLI repeats a leaf-list's value position, which accepted
             `address dhcp dhcp`.

             Multiple static addresses may be configured; the kernel
             marks an address secondary when it shares its mask and
             subnet with an existing primary on the interface (shown
             by `show interface`). Within a subnet the first address
             installed becomes the primary, so on a full config replay
             the list order decides: `ordered-by user` keeps the
             entries in the order they were set, not sorted by address.

             `dhcp` leases the interface's address from a DHCP server
             instead (the dhcpc task, docs/design/dhcp-client.md), and
             is then the only entry: a commit holding it beside a
             static address is refused. The lease's address, default
             route and classless routes go through the RIB, and its
             name servers to the host's resolver; `dhcp-options` tunes
             the client.";
          leaf address {
            ext:help "IPv4 interface address, or dhcp to acquire one";
            type union {
              type inet:ipv4-prefix;
              type enumeration {
                enum dhcp;
              }
            }
          }
        }
        container dhcp-options {
          ext:help "DHCP client options";
          description
            "Options of the DHCP client `address dhcp` starts (VyOS's
             `dhcp-options` leaves). Without `address dhcp` they are
             stored and unused.";
          leaf client-id {
            ext:help "Client identifier (option 61): xx:xx:... or text";
            type string {
              length "1..253";
            }
            description
              "Sent as option 61. Colon-separated hex octets are the
               identifier as it is; any other value is text, sent with
               type 0. Unset, no identifier is sent and the server
               keys the lease on the hardware address.";
          }
          leaf host-name {
            ext:help "Host name (option 12); default: system hostname";
            type string {
              length "1..255";
            }
          }
          leaf vendor-class-id {
            ext:help "Vendor class identifier (option 60)";
            type string {
              length "1..255";
            }
          }
          leaf user-class {
            ext:help "User class (option 77)";
            type string {
              length "1..255";
            }
          }
          leaf default-route-distance {
            ext:help "Administrative distance of the lease's routes (default 210)";
            type uint8 {
              range "1..255";
            }
            description
              "Distance of the routes the lease installs. Two DHCP
               interfaces at one distance share traffic (ECMP); at
               different distances the lower one carries it and the
               other is its backup.";
          }
          leaf no-default-route {
            ext:help "Do not install a default route from the lease";
            type empty;
          }
          leaf no-name-server {
            ext:help "Do not use the lease's name servers for the host";
            type empty;
            description
              "A lease's name servers and search domains are the host's
               own: they are handed to systemd-resolved as the
               interface's DNS configuration, and taken back when the
               lease ends (the resolver task,
               docs/design/dhcp-client.md §13); zebra-rs never writes
               resolv.conf. With this leaf they are only shown (`show
               dhcp client leases`): for an uplink whose name servers
               the host is not to ask, one in a VRF for instance, as
               systemd-resolved is not VRF-aware.";
          }
          leaf-list reject {
            ext:help "Ignore offers from this server address or prefix";
            type union {
              type inet:ipv4-address;
              type inet:ipv4-prefix;
            }
          }
        }
      }
      container ipv6 {
        ext:help "IPv6 configuration";
        list address {
          ext:help "IPv6 interface address, or autoconf for SLAAC";
          key "address";
          ordered-by user;
          description
            "IPv6 addresses assigned to the interface, one entry per
             address (a keyed list for the reason given on the IPv4
             `address` list), kept in the order they were set. Unlike
             IPv4, IPv6 interfaces routinely hold several addresses (a
             link-local plus one or more globals); each entry is
             installed to the kernel independently and removing one
             leaves the others in place.

             `autoconf` runs the RA host on the interface (the nd task,
             docs/design/dhcp-client.md §7): it solicits Router
             Advertisements, installs the default route and on-link
             prefixes they give through the RIB, hands the name servers
             they name to the host's resolver, and forms a SLAAC
             address (RFC 4862) from each autonomous /64 prefix, beside
             any address configured here — unlike IPv4's `dhcp`, it
             does not exclude static entries. `ra-options` tunes it.

             `dhcpv6` leases an address from a DHCPv6 server (the dhcpc
             task, docs/design/dhcp-client.md §8): a /128 that brings no
             connected route, since only a Router Advertisement says
             which prefixes are on-link. It runs the RA host too, for
             the default route and the on-link prefixes, but forms no
             SLAAC address unless `autoconf` is set as well. Static
             entries may stand beside it. `dhcpv6-options` tunes it.";
          leaf address {
            ext:help "IPv6 interface address, autoconf for SLAAC, or dhcpv6 to lease one";
            type union {
              type inet:ipv6-prefix;
              type enumeration {
                enum autoconf;
                enum dhcpv6;
              }
            }
          }
        }
        container ra-options {
          ext:help "RA host options";
          description
            "Options of the RA host `address autoconf` starts. VyOS has
             no counterpart: it leaves RAs to the kernel. Without
             `address autoconf` they are stored and unused.";
          leaf default-route-distance {
            ext:help "Administrative distance of the RA's routes (default 210)";
            type uint8 {
              range "1..255";
            }
            description
              "Distance of the default route and on-link prefixes the
               RA host installs. Two interfaces at one distance share
               the default (ECMP) unless their routers' preferences
               differ; at different distances the lower one carries it
               and the other is its backup.";
          }
          leaf no-default-route {
            ext:help "Do not install a default route from Router Advertisements";
            type empty;
          }
          leaf no-name-server {
            ext:help "Do not use the advertised name servers for the host";
            type empty;
            description
              "The name servers and search domains Router Advertisements
               name (RDNSS, DNSSL) are the host's own: they are handed
               to systemd-resolved as the interface's DNS configuration,
               behind those of a DHCP lease, and taken back when their
               lifetime runs out (the resolver task,
               docs/design/dhcp-client.md §13). With this leaf they are
               only shown (`show ipv6 nd interface`). The ones a lease
               names are `ipv4 dhcp-options no-name-server`'s and `ipv6
               dhcpv6-options no-name-server`'s to keep back.";
          }
        }
        container dhcpv6-options {
          ext:help "DHCPv6 client options";
          description
            "Options of the DHCPv6 client (VyOS's `dhcpv6-options`
             leaves). `address dhcpv6` starts it to lease an address,
             `pd` to have a prefix delegated, and `parameters-only` to
             ask for the other configuration alone. Without any of
             them they are stored and unused.";
          leaf duid {
            ext:help "DHCP unique identifier of this client: xx:xx:...";
            // Three octets at least, said by the pattern itself; that
            // there are no more than 130 is checked at commit
            // (config::check), since the pattern cannot count.
            type string {
              length "8..389";
              pattern '[0-9A-Fa-f][0-9A-Fa-f]:[0-9A-Fa-f][0-9A-Fa-f](:[0-9A-Fa-f][0-9A-Fa-f])+';
            }
            description
              "The DUID this interface's client presents, as
               colon-separated hex octets (3 to 130 of them). Unset,
               the system's DUID is used: a DUID-LLT made once and kept
               across restarts. A server knows a client by its DUID:
               changing it gives the lease back and asks again as
               another client.";
          }
          leaf parameters-only {
            ext:help "Ask for configuration parameters only, no address";
            type empty;
            description
              "Stateless DHCPv6 (Information-request): DNS servers, the
               search list and NTP servers, and no address. Not
               together with `address dhcpv6`.";
          }
          leaf rapid-commit {
            ext:help "Accept a two-message exchange (Rapid Commit)";
            type empty;
          }
          leaf no-release {
            ext:help "Do not release the lease when the client stops";
            type empty;
          }
          leaf no-name-server {
            ext:help "Do not use the server's name servers for the host";
            type empty;
            description
              "The name servers and search domains a DHCPv6 server
               names, with a lease or to `parameters-only`, are the
               host's own: they are handed to systemd-resolved as the
               interface's DNS configuration, behind those of a DHCPv4
               lease and ahead of the advertised ones, and taken back
               when the client gives them up (the resolver task,
               docs/design/dhcp-client.md §13). With this leaf they are
               only shown (`show dhcpv6 client leases`). The ones a
               DHCPv4 lease or Router Advertisements name are `ipv4
               dhcp-options no-name-server`'s and `ipv6 ra-options
               no-name-server`'s to keep back.";
          }
          list pd {
            ext:help "Ask for a delegated prefix (IA_PD)";
            key "id";
            description
              "Prefix delegation (RFC 8415): ask the server for a prefix
               to hand out behind this router. Each entry is one
               delegation; its `id` is the IAID of the IA_PD the client
               asks with, which is what the server keys the delegation
               on. The prefix is held with a discard route, so that
               traffic for the part of it not in use goes nowhere, not
               back out to the server. Not together with
               `parameters-only`.";
            leaf id {
              ext:help "Identifier of this delegation (IAID)";
              type uint32;
            }
            leaf length {
              ext:help "Prefix length to ask for: a hint (default 64)";
              type uint8 {
                range "32..64";
              }
              description
                "The length the client hints at. The server delegates
                 what it sees fit. Changing it gives the prefix back and
                 asks again.";
            }
            list interface {
              ext:help "Give an interface a /64 of the delegated prefix";
              key "if-name";
              description
                "An interface behind this router that is numbered from
                 the delegation: it gets an address in one /64 of the
                 prefix, for as long as the prefix is held and with the
                 prefix's lifetimes, and the /64 is then on-link there.
                 Not the interface the prefix is delegated on (RFC 8415
                 section 6.3), and in the same VRF as it. Each interface
                 of a delegation needs a /64 of its own: an `sla-id` no
                 other has.";
              leaf if-name {
                ext:help "Interface name";
                ext:dynamic "rib:interface";
                type string;
              }
              leaf sla-id {
                ext:help "Which /64 of the prefix: the subnet's number (default 0)";
                type uint32;
                description
                  "The number of the /64 within the delegated prefix:
                   the bits between the prefix's length and 64. A /56
                   has 256 of them, 0 to 255; a /64 is its own only
                   subnet, 0. A number the prefix the server delegates
                   has no room for leaves the interface without an
                   address, which the log and `show dhcpv6 client
                   leases` say.";
              }
              leaf address {
                ext:help "Host part of the interface's address (default: from its MAC, EUI-64)";
                type uint64 {
                  range "1..18446744073709551615";
                }
                description
                  "The low 64 bits of the address: 1 gives `<subnet>::1`.
                   Unset, they are made from the interface's hardware
                   address (modified EUI-64), which an interface without
                   one, a loopback for one, cannot do.";
              }
            }
          }
        }
      }
    }
    list vrf {
      ext:help "VRF routing instance";
      ext:sort "30";
      key "name";
      description
        "BGP/MPLS L3VPN Virtual Routing and Forwarding instance.
         The optional ipv4 / ipv6 containers carry the per-address-
         family Route Target import/export policy.";
      leaf name {
        ext:help "VRF name";
        type string;
        description
          "Operator-assigned VRF identifier (e.g. CUST-A). Keys this
           list and is the handle used everywhere else in config.
           The numeric VRF / kernel routing-table ID is assigned
           internally by zebra-rs and is not user-configurable.";
      }
      leaf router-id {
        ext:help "Router identifier for this VRF";
        description
          "Per-VRF Router ID override. When absent, zebra-rs derives
           one from the VRF's member interfaces (loopback-flagged
           members first), falling back to the global effective
           Router ID. Pushed to this VRF's protocol subscribers via
           RouterIdUpdate, like the global `system router-id`.";
        type inet:ipv4-address;
      }
      leaf mpls-ttl-propagate {
        ext:help "Per-VRF MPLS TTL model (overrides the global mpls ttl propagate)";
        description
          "Per-VRF RFC 3443 MPLS label-TTL model for this VRF's L3VPN
           LSPs (imposition of the VPN label and pop-to-IP disposition).
           `inherit` (default) uses the global `mpls ttl propagate`;
           `pipe` hides the LSP; `uniform` exposes the hop count. Honored
           by the cradle eBPF data plane; the kernel FIB is unaffected.
           Configure the same model on the ingress and egress PEs of a
           VRF, since the two ends of an LSP must agree.";
        type enumeration {
          enum inherit;
          enum pipe;
          enum uniform;
        }
        default "inherit";
      }
      container ipv4 {
        ext:help "IPv4 unicast (VPNv4) route policy";
        description
          "IPv4 unicast (VPNv4 / RFC 4364) route policy for this VRF.";
        uses vrf-route-target-policy;
      }
      container ipv6 {
        ext:help "IPv6 unicast (VPNv6) route policy";
        description
          "IPv6 unicast (VPNv6 / RFC 4659) route policy for this VRF.";
        uses vrf-route-target-policy;
      }
      container mup {
        ext:help "BGP MUP route policy";
        description
          "BGP MUP (draft-ietf-bess-mup-safi) route policy for
           this VRF. The export RTs tag the Session-Transformed routes the
           MUP controller originates from this VRF; the import RTs select
           which received ST routes belong to it (the import side is
           reserved for the MUP import dispatch follow-up). Same
           `route-target {import|export}` shape as ipv4 / ipv6.";
        uses vrf-route-target-policy;
      }
    }
    list policy {
      ext:help "Routing policy (route-map)";
      ext:sort "4";
      key "name";
      leaf "name" {
        ext:help "Policy name";
        type string;
      }
      list entry {
        ext:help "Policy entry (clause)";
        ext:sort "5";
        key "number";
        leaf "number" {
          ext:help "Entry sequence number";
          type uint32;
        }
        container "match" {
          ext:help "Match conditions";
          ext:sort "7";
          leaf "prefix-set" {
            ext:help "Match a prefix-set by name";
            type string;
            description
              "Reference to a `prefix-set` by name.";
          }
          leaf "community" {
            ext:help "Match a community-set by name";
            type string;
            description
              "Reference to a `community-set` by name.";
          }
          leaf "ext-community" {
            ext:help "Match an ext-community-set by name";
            type string;
            description
              "Reference to an `ext-community-set` by name. The
               set's members are checked against the route's
               EXT_COMMUNITIES attribute.";
          }
          leaf "large-community" {
            ext:help "Match a large-community-set by name";
            type string;
            description
              "Reference to a `large-community-set` by name. The
               set's members are checked against the route's
               LARGE_COMMUNITIES attribute.";
          }
          leaf "as-path" {
            ext:help "Match an as-path-set by name";
            type string;
            description
              "Reference to an `as-path-set` by name.";
          }
          leaf "next-hop" {
            ext:help "Match the BGP next-hop address";
            type union {
              type inet:ipv4-address;
              type inet:ipv6-address;
            }
            description
              "Direct IP address. Compared for exact equality
               against the route's BGP NEXT_HOP attribute. To
               match a range of addresses, use `match prefix`
               with a prefix-set instead.";
          }
          container "med" {
            ext:help "Match the MED (MULTI_EXIT_DISC)";
            presence "match med";
            description
              "Match the route's MULTI_EXIT_DISC against a single
               operator + value. Exactly one of `eq`, `le`, `ge`
               must be set when the container is present —
               schema-enforced via the `op` choice.";
            choice "op" {
              mandatory true;
              description
                "Comparison operator. Each case carries a
                 mandatory uint32 operand; the bare-keyword case
                 names mirror the CLI shape `match med eq NUM`,
                 `match med le NUM`, `match med ge NUM`.";
              case eq-case {
                leaf "eq" {
                  ext:help "Equal to this value";
                  type uint32;
                }
              }
              case le-case {
                leaf "le" {
                  ext:help "Less than or equal to this value";
                  type uint32;
                }
              }
              case ge-case {
                leaf "ge" {
                  ext:help "Greater than or equal to this value";
                  type uint32;
                }
              }
            }
          }
          container "as-path-len" {
            ext:help "Match the AS_PATH length";
            presence "match as-path-len";
            description
              "Match the total length of the route's AS_PATH
               (count of ASes across all segments) against
               `eq`/`le`/`ge` NUM. Same shape as `match med`.";
            choice "op" {
              mandatory true;
              case eq-case {
                leaf "eq" {
                  ext:help "Equal to this value";
                  type uint32;
                }
              }
              case le-case {
                leaf "le" {
                  ext:help "Less than or equal to this value";
                  type uint32;
                }
              }
              case ge-case {
                leaf "ge" {
                  ext:help "Greater than or equal to this value";
                  type uint32;
                }
              }
            }
          }
          container "as-path-len-uniq" {
            ext:help "Match count of distinct ASes";
            presence "match as-path-len-uniq";
            description
              "Match the count of distinct ASes in the route's
               AS_PATH (duplicates collapsed) against
               `eq`/`le`/`ge` NUM. Same shape as `match med`.";
            choice "op" {
              mandatory true;
              case eq-case {
                leaf "eq" {
                  ext:help "Equal to this value";
                  type uint32;
                }
              }
              case le-case {
                leaf "le" {
                  ext:help "Less than or equal to this value";
                  type uint32;
                }
              }
              case ge-case {
                leaf "ge" {
                  ext:help "Greater than or equal to this value";
                  type uint32;
                }
              }
            }
          }
          container "local-preference" {
            ext:help "Match LOCAL_PREF value";
            presence "match local-preference";
            description
              "Match the route's LOCAL_PREF attribute against
               `eq`/`le`/`ge` NUM. Same shape as `match med`.";
            choice "op" {
              mandatory true;
              case eq-case {
                leaf "eq" {
                  ext:help "Equal to this value";
                  type uint32;
                }
              }
              case le-case {
                leaf "le" {
                  ext:help "Less than or equal to this value";
                  type uint32;
                }
              }
              case ge-case {
                leaf "ge" {
                  ext:help "Greater than or equal to this value";
                  type uint32;
                }
              }
            }
          }
          container "weight" {
            ext:help "Match the BGP weight";
            presence "match weight";
            description
              "Match the route's BGP weight (per-router,
               implementation attribute) against `eq`/`le`/`ge`
               NUM. Same shape as `match med`.";
            choice "op" {
              mandatory true;
              case eq-case {
                leaf "eq" {
                  ext:help "Equal to this value";
                  type uint32;
                }
              }
              case le-case {
                leaf "le" {
                  ext:help "Less than or equal to this value";
                  type uint32;
                }
              }
              case ge-case {
                leaf "ge" {
                  ext:help "Greater than or equal to this value";
                  type uint32;
                }
              }
            }
          }
          leaf "origin" {
            ext:help "Match the ORIGIN attribute";
            type enumeration {
              enum igp;
              enum egp;
              enum incomplete;
            }
          }
          leaf "tag" {
            ext:help "Match the route tag";
            type uint32;
            description
              "Match routes carrying this tag. The tag is a non-wire
               per-route marker stamped by `set tag`, kept on the route
               in the RIB so a policy in one direction can match what a
               policy in the other direction set. 0 means untagged and
               cannot be matched, matching FRR.";
          }
          leaf "color" {
            ext:help "Match the BGP Color community";
            type uint32;
            description
              "Match a BGP Color Extended Community (RFC 9012 §4.3,
               opaque type 0x03 sub-type 0x0b) by value. The CO bits
               in the Flags field are not compared in this revision —
               only the 32-bit color value. At least one matching
               entry in the route's EXT_COMMUNITIES attribute satisfies
               the predicate.";
          }
          container "evpn" {
            ext:help "Match EVPN route attributes";
            description
              "Match EVPN route attributes. `route-type` selects
               one of the BGP-EVPN NLRI route types (RFC 7432
               §7.1–7.5; RFC 9136 for Type-5); `vni` matches a
               specific VXLAN Network Identifier carried in the
               route (encapsulation extended community or
               Type-2/Type-3 MPLS label field).";
            leaf "route-type" {
              ext:help "Match the EVPN route type";
              type enumeration {
                enum ead {
                  description
                    "EAD (Type-1) route";
                }
                enum macip {
                  description
                    "MAC-IP (Type-2) route";
                }
                enum multicast {
                  description
                    "Multicast (Type-3) route";
                }
                enum es {
                  description
                    "Ethernet Segment (Type-4) route";
                }
                enum prefix {
                  description
                    "Prefix (Type-5) route";
                }
                enum smet {
                  description
                    "Selective Multicast Ethernet Tag (Type-6) route";
                }
              }
              description
                "Match EVPN route type.";
            }
            leaf "vni" {
              ext:help "Match the EVPN VNI";
              type uint32 {
                range "1..16777215";
              }
              description
                "Match EVPN VNI ID.";
            }
          }
        }
        container "set" {
          ext:help "Set (modify) route attributes";
          ext:sort "3";
          container "local-preference" {
            ext:help "Set the LOCAL_PREF attribute";
            presence "set local-preference";
            description
              "Set the route's LOCAL_PREF attribute. Exactly one
               of `set` (overwrite), `add` (saturating add to the
               current value, treating absence as 0), or `sub`
               (saturating subtract) must be present.";
            choice "op" {
              mandatory true;
              case set-case {
                leaf "set" {
                  ext:help "Overwrite with this value";
                  type uint32;
                }
              }
              case add-case {
                leaf "add" {
                  ext:help "Add to the current value";
                  type uint32;
                }
              }
              case sub-case {
                leaf "sub" {
                  ext:help "Subtract from the current value";
                  type uint32;
                }
              }
            }
          }
          container "med" {
            ext:help "Set the MED (MULTI_EXIT_DISC)";
            presence "set med";
            description
              "Set the route's MULTI_EXIT_DISC. Same shape as
               `set local-preference`: choice of `set`/`add`/`sub`
               with a uint32 operand. `add`/`sub` saturate.";
            choice "op" {
              mandatory true;
              case set-case {
                leaf "set" {
                  ext:help "Overwrite with this value";
                  type uint32;
                }
              }
              case add-case {
                leaf "add" {
                  ext:help "Add to the current value";
                  type uint32;
                }
              }
              case sub-case {
                leaf "sub" {
                  ext:help "Subtract from the current value";
                  type uint32;
                }
              }
            }
          }
          leaf "weight" {
            ext:help "Set the local BGP weight";
            type uint32;
            description
              "Set the route's local BGP weight. Higher weight
               wins in best-path selection. Default 0 (unless
               the route is locally originated). Weight is
               per-router and is not advertised in BGP
               updates.";
          }
          container "next-hop" {
            ext:help "Set the BGP next-hop";
            presence "set next-hop";
            description
              "Set the route's BGP NEXT_HOP attribute. Either an
               explicit IPv4/IPv6 address, or the keyword `self`,
               which resolves at apply time to the local router
               identifier used for the session that's advertising
               the route. Whether an IPv6 address reaches the wire
               depends on the family: a Link-State advertisement
               carries its next hop in MP_REACH and honours it, while
               the traditional NEXT_HOP attribute of IPv4 unicast
               cannot express one and ignores it.";
            choice "target" {
              mandatory true;
              case address-case {
                leaf "address" {
                  ext:help "Next-hop IP address";
                  type union {
                    type inet:ipv4-address;
                    type inet:ipv6-address;
                  }
                }
              }
              case self-case {
                leaf "self" {
                  ext:help "Use this router as the next-hop";
                  type empty;
                }
              }
            }
          }
          leaf "origin" {
            ext:help "Set the ORIGIN attribute";
            type enumeration {
              enum igp;
              enum egp;
              enum incomplete;
            }
            description
              "Set the route's ORIGIN attribute. Mirrors the
               three values that `match origin` accepts.";
          }
          leaf "tag" {
            ext:help "Set the route tag";
            type uint32;
            description
              "Stamp the route with this tag. The tag is not carried on
               the wire — it rides with the route in the RIB so a later
               policy, including one in the other direction, can match
               it. 0 means untagged.";
          }
          leaf "color" {
            ext:help "Set the BGP Color community";
            type uint32;
            description
              "Append a BGP Color Extended Community (RFC 9012 §4.3)
               with the given value and CO bits = 00 to the route's
               EXT_COMMUNITIES attribute. The mapping from color to
               IS-IS Flex-Algorithm lives under
               `/router/bgp/color-policy`.";
          }
          container "prefix-sid" {
            ext:help "Set the BGP Prefix-SID attribute";
            presence "set prefix-sid";
            description
              "Install a BGP Prefix-SID attribute (RFC 8669, attr 40)
               on the route. Today only the Label-Index TLV is
               settable; Originator-SRGB and SRv6 service TLVs are
               populated by other code paths.";
            leaf "label-index" {
              ext:help "Prefix-SID label index (RFC 8669)";
              type uint32;
              description
                "Replace the route's Prefix-SID attribute with a
                 single Label-Index TLV whose flags = 0 and
                 label-index = the given value. RFC 8669 §3.1.";
            }
          }
          container "community" {
            ext:help "Set/add/delete route communities";
            presence "set community";
            description
              "Apply a community-set to the route. The choice
               between {replace-case|additive-case|delete-case}
               selects the operation: replace (default) overwrites
               the COMMUNITIES attribute with the set's members,
               additive merges them in, delete removes them from
               the existing attribute (set difference).";
            leaf "name" {
              ext:help "Community-set to apply";
              type string;
              mandatory true;
              description
                "Reference to a community-set by name.";
            }
            choice "mode" {
              default replace-case;
              description
                "Operation applied to the route's COMMUNITIES
                 attribute. The bare-keyword `additive` and
                 `delete` cases mirror the CLI shape.";
              case replace-case {
                description "Default — overwrite the attribute.";
              }
              case additive-case {
                leaf "additive" {
                  ext:help "Merge into existing communities";
                  type empty;
                  description
                    "Merge the set's members into the existing
                     COMMUNITIES attribute.";
                }
              }
              case delete-case {
                leaf "delete" {
                  ext:help "Remove from existing communities";
                  type empty;
                  description
                    "Remove the set's members from the existing
                     COMMUNITIES attribute.";
                }
              }
            }
          }
          container "ext-community" {
            ext:help "Set/add/delete route extended communities";
            presence "set ext-community";
            description
              "Apply an ext-community-set to the route. Same
               {replace|additive|delete} choice as `set community`,
               applied to the EXT_COMMUNITIES attribute. Only exact
               `rt:`/`soo:` members of the set contribute concrete
               values; regex members are skipped. replace (default)
               overwrites the attribute — including any route targets
               or Color community already present — so use additive to
               preserve them.";
            leaf "name" {
              ext:help "Ext-community-set to apply";
              type string;
              mandatory true;
              description
                "Reference to an ext-community-set by name.";
            }
            choice "mode" {
              default replace-case;
              description
                "Operation applied to the route's EXT_COMMUNITIES
                 attribute.";
              case replace-case {
                description "Default — overwrite the attribute.";
              }
              case additive-case {
                leaf "additive" {
                  ext:help "Merge into existing ext-communities";
                  type empty;
                  description
                    "Merge the set's members into the existing
                     EXT_COMMUNITIES attribute.";
                }
              }
              case delete-case {
                leaf "delete" {
                  ext:help "Remove from existing ext-communities";
                  type empty;
                  description
                    "Remove the set's members from the existing
                     EXT_COMMUNITIES attribute.";
                }
              }
            }
          }
          container "large-community" {
            ext:help "Set/add/delete route large communities";
            presence "set large-community";
            description
              "Apply a large-community-set to the route. Same
               {replace|additive|delete} choice as `set community`,
               applied to the LARGE_COMMUNITIES attribute. Only exact
               `A:B:C` members contribute concrete values; regex
               members are skipped.";
            leaf "name" {
              ext:help "Large-community-set to apply";
              type string;
              mandatory true;
              description
                "Reference to a large-community-set by name.";
            }
            choice "mode" {
              default replace-case;
              description
                "Operation applied to the route's LARGE_COMMUNITIES
                 attribute.";
              case replace-case {
                description "Default — overwrite the attribute.";
              }
              case additive-case {
                leaf "additive" {
                  ext:help "Merge into existing large communities";
                  type empty;
                  description
                    "Merge the set's members into the existing
                     LARGE_COMMUNITIES attribute.";
                }
              }
              case delete-case {
                leaf "delete" {
                  ext:help "Remove from existing large communities";
                  type empty;
                  description
                    "Remove the set's members from the existing
                     LARGE_COMMUNITIES attribute.";
                }
              }
            }
          }
          container "as-path-prepend" {
            ext:help "Prepend an AS to AS_PATH";
            presence "Prepend `asn` onto AS_PATH `repeat` times.";
            description
              "Prepend a single AS number to AS_PATH. The same `asn`
               is prepended `repeat` times — equivalent to IOS-XR's
               `prepend as-path NUM repeats N` and the typical
               BGP traffic-engineering knob for biasing best-path
               selection on the receiver.";
            leaf "asn" {
              ext:help "AS number to prepend";
              type inet:as-number;
              mandatory true;
              description
                "AS number to prepend onto AS_PATH.";
            }
            leaf "repeat" {
              ext:help "Times to prepend the AS (default 1)";
              type uint8 {
                range "1..255";
              }
              default "1";
              description
                "Number of times to prepend `asn`. Default 1.";
            }
          }
        }
        leaf "call" {
          ext:help "Run another policy from this entry";
          ext:sort "2";
          type string;
          description
            "Name of a policy to evaluate when this entry matches. The
             callee runs after this entry's match clauses and before its
             terminal action: if the callee denies, this policy denies;
             if it permits, evaluation continues with this entry's own
             set clauses and action. Set clauses applied inside the
             callee are kept either way.

             A plain string rather than a leafref, matching the
             prefix-set and community-set references, so a policy may be
             configured before the policy it calls. Chain length is not
             limited; a call cycle is refused and the entries on it deny,
             following the rule that a bound-but-unresolved reference is
             deny-all.";
        }
        leaf "action" {
          ext:help "Terminal action: permit, deny, or next";
          ext:sort "1";
          mandatory true;
          description
            "Terminal action when the entry matches. Mandatory
             on every entry; the policy walker honors the value.
             `permit` accepts the route and stops scanning, after
             applying any `set` clauses.
             `deny` rejects the route. No `set` clauses are
             applied.
             `next` applies any `set` clauses, then falls through
             to the next entry. Default-deny applies when no entry
             matches (or all matching entries fall through with
             `next`).";
          type enumeration {
            enum permit;
            enum deny;
            enum next;
          }
        }
      }
    }
  }
}

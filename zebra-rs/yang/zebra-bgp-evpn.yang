module zebra-bgp-evpn {
  yang-version "1";

  namespace "urn:ietf:params:xml:ns:yang:zebra-bgp-evpn";
  prefix "zbe";

  import ietf-bgp {
    prefix bgp;
  }

  import config {
    prefix config;
  }

  import configure {
    prefix configure;
  }

  import ietf-inet-types {
    prefix inet;
  }


  organization
    "zebra-rs";

  contact
    "https://github.com/zebra-rs";

  description
    "EVPN service extensions to the BGP candidate-config tree.

     Adds the FRR-style `advertise-all-vni` knob under the BGP
     global AFI/SAFI list — when enabled for the `evpn`
     AFI/SAFI, every locally-configured VXLAN VNI participates in
     EVPN advertisement (Type-2 MAC/IP + Type-3 Inclusive Multicast)
     with auto-derived RD and RT.

     Resulting CLI / config shape:

       router bgp {
         neighbor 10.0.0.1 {
           remote-as 65001;
           afi-safi {
             name evpn;
             enabled true;
           }
         }
         afi-safi {
           name evpn;
           advertise-all-vni true;
         }
       }

     IOS-XR-style per-VNI configuration (explicit RD / route-target
     per VNI) is a follow-up.";

  reference
    "RFC 7432: BGP MPLS-Based Ethernet VPN
     RFC 8365: Network Virtualization Overlay Solution Using EVPN
     RFC 9574: Optimized Ingress Replication Solution for EVPN";

  grouping bgp-afi-safi-evpn-extension {
    description
      "Per-AFI/SAFI EVPN extensions on the global afi-safi list. Only
       meaningful when the list entry's name is `bt:evpn` —
       harmless and ignored on other AFI/SAFIs.";
    leaf kernel-route-exchange {
      ext:help "Install EVPN prefixes through Linux L3-VNI bridges";
      type boolean;
      default false;
      description
        "Import VXLAN Type-5 routes through the adopted L3-VNI bridge,
         using the remote VTEP and router MAC. The Linux bridge, VXLAN
         FDB and neighbor tables describe the overlay adjacency. This
         supports kernel forwarding and consumers of kernel state.
         Changing it with routes installed moves them between this
         install and the ordinary one.";
    }
    leaf advertise-all-vni {
      ext:help "Advertise routes for all local VNIs";
      type boolean;
      default false;
      description
        "When true, advertise EVPN Type-2 (MAC/IP) and Type-3
         (Inclusive Multicast) routes for every locally-configured
         VXLAN VNI. Bridge -> VNI mapping is inferred from the kernel
         (the VXLAN slave of each bridge supplies the VNI). RD is
         auto-derived as <router-id>:<VNI> per RFC 8365 §5.1.2;
         import / export RT is auto-derived as <local-AS>:<VNI>.

         Equivalent to FRR's `advertise-all-vni` under
         `address-family l2vpn evpn`.

         Like FRR, this never originates a Type-2 for one of this
         node's own addresses — the bridge's (SVI) MAC or an enslaved
         port's MAC, the rows the kernel FDB reports as `permanent`.
         Those are not stations behind a port, and a peer that
         installed them would treat this node's gateway as a remote
         host. Rows an operator parks with `bridge fdb add ... static`
         are stations and are advertised. There is no equivalent of
         FRR's `advertise-svi-ip` / `advertise-default-gw` yet.";
    }
    container dup-addr-detection {
      ext:help "EVPN duplicate address detection (RFC 7432 section 15.1)";
      description
        "Detect a MAC, or an IP moving between MACs, that moves between
         this node and a remote VTEP `max-moves` times within `time`
         seconds: two hosts, or a loop, claiming one address. On by
         default, as in FRR (`dup-addr-detection` under `address-family
         l2vpn evpn`). A detected address is logged and shown by `show
         evpn dup-addr`; with `freeze` it is also neither advertised nor
         installed from remote routes until the freeze ends or `clear bgp
         evpn dup-addr` releases it.";
      leaf enabled {
        ext:help "Run duplicate address detection";
        type boolean;
        default true;
        description
          "Turning detection off releases every detected address and
           forgets every move counted so far.";
      }
      leaf max-moves {
        ext:help "Moves within the window that make a duplicate";
        type uint32 {
          range "2..1000";
        }
        default 5;
        description "RFC 7432's N.";
      }
      leaf time {
        ext:help "Detection window in seconds";
        type uint32 {
          range "2..1800";
        }
        default 180;
        description
          "RFC 7432's M. A local learn of an address that was remote
           opens the window; moves counted within it add up.";
      }
      leaf freeze {
        ext:help "Hold a duplicate: permanent, or seconds (30-3600)";
        type union {
          type enumeration {
            enum permanent;
          }
          type uint32 {
            range "30..3600";
          }
        }
        description
          "Hold a detected duplicate in its last state: this node stops
           advertising it and stops installing remote routes for it. A
           number of seconds releases it after that long; `permanent`
           only on `clear bgp evpn dup-addr`. Unset, detection only
           warns.";
      }
    }
    leaf encapsulation {
      ext:help "EVPN overlay encapsulation (vxlan, srv6 or mpls)";
      type enumeration {
        enum vxlan {
          description
            "VXLAN tunnels (RFC 8365) — the kernel bridge/VXLAN FDB
             data plane. The default.";
        }
        enum srv6 {
          description
            "SRv6 (RFC 9252) — advertise a per-VNI End.DT2U SID on
             Type-2 (MAC/IP) routes and an End.DT2M SID on Type-3
             (IMET) routes, carved from the BGP SRv6 locator, and
             install received MACs against the peer's L2 service SIDs.
             Requires `segment-routing srv6 locator`; the L2 data
             plane is the cradle eBPF tee (`system cradle enabled`,
             with an engine from `system ebpf enabled` or run
             externally) — the kernel has no End.DT2U/DT2M seg6local
             actions.";
        }
        enum mpls {
          description
            "MPLS (RFC 7432) — EVPN's base encapsulation. Type-2 and
             Type-3 routes carry a per-EVI MPLS service label, imposed
             under whatever transport LSP reaches the egress PE, which
             pops it into the EVI's bridge domain. Bridge domains are
             declared explicitly with the `evi` list (there is no VXLAN
             device to read a VNI from). The L2 data plane is the
             cradle eBPF tee (`system cradle enabled`, with an engine
             from `system ebpf enabled` or run externally) — the
             kernel has no action that pops a label into a bridge.";
        }
      }
      default vxlan;
      description
        "EVPN overlay encapsulation for locally originated and
         received MAC routes. This is the L2 (Type-2 / Type-3) service;
         Type-5 (IP Prefix) is an L3 service and takes its
         encapsulation from the VRF's own `encapsulation` leaf.

         VPWS E-Line services (the `vpws` list) originate under this
         encapsulation too: their Type-1 carries an End.DX2/DX2V
         L2-Service SID under srv6, the service VNI in the label field
         plus the VXLAN Encapsulation extended community under vxlan
         (RFC 8365 §6), or a per-service MPLS label (drawn from the
         same dynamic block as VRF and EVI labels) with no
         Encapsulation EC under mpls (RFC 8365 §5.1.3). The *receive*
         side is not gated by this leaf: each direction of an E-Line
         uses the encapsulation its originator signalled.";
    }
    leaf vtep-source {
      ext:help "EVPN source address (next hop / origin) when no VXLAN device supplies one";
      type inet:ip-address;
      description
        "This PE's EVPN source address — IPv4 or IPv6 — used wherever a
         locally originated EVPN route needs an address and no local
         VXLAN device supplies one: the next hop of a VPWS Type-1 or a
         deviceless Type-2/Type-5, the Originating Router IP of an
         `encapsulation mpls` IMET, and the originator of Ethernet
         Segment routes (also the DF election's self-identity). Without
         it those fall back to the IPv4 router-id, which cannot express
         a PE on an IPv6 underlay — under `encapsulation vxlan` the
         address is the VTEP, under `mpls` it is the address the
         transport LSP resolves on. Routes whose VNI does have a local
         VXLAN device keep taking that device's local address.";
    }
    list evi {
      ext:help "EVPN Instance (bridge domain) for `encapsulation mpls`";
      key "id";
      description
        "An EVPN Instance — one bridge domain advertised into EVPN.

         Only needed with `encapsulation mpls`. The vxlan and srv6
         paths infer which bridge domains to advertise, and their
         service identifier, from a local VXLAN device's VNI; an MPLS
         EVI has no VNI, so the operator names the bridge and the
         instance id here.

         The id doubles as the bridge domain and as the low 24 bits of
         the auto-derived RD (<router-id>:<id>) and route target
         (<local-AS>:<id>), so it is interchangeable with a VNI
         everywhere else in the EVPN path — matching the `evi` leaf
         the vpws list already uses.";
      leaf id {
        ext:help "EVPN Instance id";
        type uint32 {
          range "1..16777215";
        }
        description
          "EVPN Instance identifier (the list key). Both PEs of a
           service must agree on it.";
      }
      leaf bridge {
        ext:help "Bridge interface carrying this EVI's L2 domain";
        type string;
        description
          "Name of the bridge interface whose L2 domain this EVI
           carries — its CE-facing ports are the attachment circuits,
           and MACs learned there are advertised as Type-2 routes
           under this EVI's RD and route target.";
      }
    }
    leaf igmp-mld-proxy {
      ext:help "Advertise IGMP/MLD proxy capability (RFC 9251)";
      type boolean;
      default false;
      description
        "When true, advertise IGMP/MLD proxy capability (RFC 9251 §6)
         by attaching the Multicast Flags Extended Community (both the
         IGMP and MLD proxy bits) to every locally originated Type-3
         (Inclusive Multicast) route. This tells remote PEs they may
         send selective multicast (Type-6 SMET) toward this PE instead
         of flooding BUM for snooped groups. Per-protocol granularity
         (IGMP-only / MLD-only) is a follow-up.";
    }
    leaf segmentation {
      ext:help "Advertise BUM tunnel segmentation (RFC 9572)";
      type boolean;
      default false;
      description
        "When true, advertise BUM tunnel-segmentation support (RFC 9572
         Section 8) by setting bit 8 of the Multicast Flags Extended
         Community on every locally originated Type-3 (Inclusive Multicast)
         route. Tells peers and Regional Border Routers that this PE
         supports the RFC 9572 segmentation procedures.";
    }
    list ethernet-segment {
      ext:help "EVPN Ethernet Segment, a multihomed CE (RFC 7432)";
      key "name";
      description
        "EVPN Ethernet Segment (RFC 7432) — a CE multihomed to two or more
         PEs. Identified to the overlay by a 10-octet ESI; the PEs on the
         same ES discover one another (Type-4 route + ES-Import RT) and run
         Designated-Forwarder election. Setting the ESI originates the
         Type-4 and the per-ES Type-1 A-D (mass withdraw); a `vpws` service
         naming this segment elects its RFC 8214 §5 role over it. The VXLAN
         data plane (DF-gated BUM, split-horizon, aliasing) is a later
         phase.";
      leaf name {
        ext:help "Ethernet Segment name";
        type string;
        description "Operator-chosen Ethernet Segment name (the list key).";
      }
      leaf esi {
        ext:help "10-octet Ethernet Segment Identifier";
        type string;
        description
          "10-octet Ethernet Segment Identifier, colon-hex (00:11:..:99) or
           20 bare hex digits. Manual Type-0 ESI in this phase.";
      }
      leaf redundancy-mode {
        ext:help "All-active or single-active multihoming";
        type enumeration {
          enum all-active {
            description
              "All PEs on the ES forward to/from the CE (load-balanced).";
          }
          enum single-active {
            description
              "Only the Designated Forwarder forwards per service; the rest
               are backup.";
          }
        }
        default all-active;
        description "All-active (default) or single-active multihoming.";
      }
      leaf interface {
        ext:help "Access interface (CE-facing port) for this ES";
        type string;
        description "Access interface (CE-facing port) bound to this ES.";
      }
      leaf role-signaling {
        ext:help "How remote PEs learn which PE forwards this segment";
        type enumeration {
          enum inferred {
            description
              "Advertise nothing; a remote PE infers the forwarder from
               which PE advertised the segment's MACs.";
          }
          enum l2-attr {
            description
              "Advertise the elected role in the Layer-2 Attributes
               extended community of the per-EVI Ethernet A-D.";
          }
        }
        default inferred;
        description
          "How a remote PE learns which PE forwards this **single-active**
           segment's known unicast. RFC 7432 does not say: the DF election
           is local to the segment's PEs, and nothing on the wire tells an
           ingress PE its outcome.

           `inferred` (the default, and the pre-existing behaviour) leaves
           the remote to deduce it from which PE advertised the segment's
           MAC routes — only the DF learns from the CE, so the deduction is
           usually right. It has two costs: before the CE has sourced
           anything there is nothing to deduce from, and after a DF change
           the old DF's MAC routes are still valid, so the remote follows
           only as the MACs are relearned.

           `l2-attr` advertises the role instead: the per-EVI Ethernet A-D
           carries the Layer-2 Attributes extended community with P=1 on the
           Designated Forwarder, B=1 on the election's runner-up and neither
           bit on any other PE (draft-ietf-bess-rfc7432bis §7.11.1). A role
           change is then an attribute-only update on a route that is
           already there, so the remote re-points without a withdraw and a
           re-selection.

           The draft is work in progress and does not specify the ingress
           procedure, so this is off by default; turn it on across a segment
           rather than on one PE. All-active segments never carry P/B — every
           attached PE forwards there.";
      }
      container df-election {
        presence "Designated-Forwarder election tuning";
        ext:help "Designated-Forwarder election tuning";
        description
          "Designated-Forwarder election parameters advertised in this
           segment's Type-4 DF Election extended community (RFC 8584 §2.2).
           Absent = the RFC 7432 §8.5 default: service carving, no
           capabilities.";
        leaf algorithm {
          ext:help "DF election algorithm: default, hrw, preference or lowest-preference";
          type enumeration {
            enum default {
              description "RFC 7432 §8.5 service carving (RFC 8584 Alg 0).";
            }
            enum hrw {
              description "RFC 8584 §3 Highest Random Weight (Alg 1).";
            }
            enum preference {
              description
                "RFC 9785 Highest-Preference (Alg 2): the highest
                 `preference` wins the whole segment.";
            }
            enum lowest-preference {
              description
                "RFC 9785 Lowest-Preference (Alg 3): the same ranking with
                 the preference comparison reversed.";
            }
          }
          description
            "The DF election algorithm this segment advertises in its Type-4
             DF Election extended community and runs locally.

             `hrw` (RFC 8584 §3, Alg 1) ranks the segment's PEs by a
             pseudo-random weight of (Ethernet Tag, ESI, PE address) — the
             highest wins, ties go to the lowest address, the runner-up is
             the backup — which spreads service instances across the PEs
             like carving does but keeps every other instance's DF unchanged
             when a PE joins or leaves.

             `preference` / `lowest-preference` (RFC 9785, Alg 2 / Alg 3)
             elect by the operator's `preference` instead of a hash, so one
             PE is Designated Forwarder for **every** Ethernet Tag on the
             segment. That is what makes deterministic active/standby
             possible: give every segment on the intended active PE the
             better preference. Carving and HRW cannot express it — they
             deliberately spread the tags.

             A configured `preference` still overrides the `default` and
             `hrw` arms, as it did before this leaf had preference arms: a
             segment spelled that way keeps advertising Alg 2 across an
             upgrade instead of switching to Alg 1 and dropping the whole
             segment to carving on the RFC 8584 unanimity check. Beside the
             two preference arms a `preference` value simply selects which
             of them bids. `show bgp evpn ethernet-segment` names the
             override where it applies.

             As with any algorithm, all PEs on the segment must advertise the
             same one (RFC 8584 §2.2) or the segment falls back to carving —
             the same show command names that disagreement too.";
        }
        leaf preference {
          ext:help "DF preference; highest wins (selects Alg 2)";
          type uint16 {
            range "0..65535";
          }
          description
            "Setting a preference switches this segment to preference-based
             DF election (Alg 2, draft-ietf-bess-evpn-pref-df): the PE with
             the **highest** preference becomes the Designated Forwarder,
             ties broken by the lowest originating address. Unset = service
             carving (Alg 0), where the DF is `service-id mod N` over the
             address-ordered PEs.

             Preference is per-segment, so one PE wins every service
             instance on it — which is the point: it lets the operator pin
             the DF instead of accepting a hash. Carving instead spreads
             instances across the PEs.

             Selecting a preference algorithm through `algorithm` and leaving
             this leaf unset bids RFC 9785 §3's mandatory default of 32767,
             the midpoint of the range — not 0, which would rank this PE
             below every peer that took the default. Ties are broken by
             `dont-preempt`, then by the lowest originating address.

             All PEs on the segment must advertise the same algorithm; RFC
             8584 negotiation falls the whole segment back to carving if any
             one of them disagrees. Interoperates with IOS-XR
             `service-carving preference-based`, Junos
             `df-election-type preference`, Arista
             `designated-forwarder election algorithm preference` and FRR
             `evpn mh es-df-pref`.";
        }
        container fast-recovery {
          presence "RFC 9722 synchronized service carving";
          ext:help "Carve at an announced instant instead of on a local timer";
          must "not(../startup-delay)" {
            error-message
              "fast-recovery and startup-delay are mutually exclusive: the
               startup delay withholds the Type-4 that a carving time has to
               be advertised on.";
          }
          description
            "RFC 9722 Fast Recovery. Without it, a PE joining a segment waits
             out a local timer and then carves, while the PEs already on the
             segment re-carve the moment its routes arrive — so the two ends
             move at different times, and a single-active segment spends that
             difference with either no Designated Forwarder or two of them.
             One drops frames, the other duplicates them and can loop.

             With it, a joining PE advertises the instant at which it will
             carve — a Service Carving Time extended community on its Type-4 —
             and every PE on the segment carves at that one instant instead of
             whenever BGP happened to deliver. The segment must agree: the
             capability is advertised in the DF Election extended community
             and synchronized carving takes effect only once **every** PE on
             the segment signals it, exactly as AC-DF does. A PE that does not
             would carve on its own timer while the others waited, which is
             worse than not synchronizing at all.

             Mutually exclusive with `startup-delay`, which withholds the
             Type-4 an announcement must ride on.";
          leaf peering-time {
            ext:help "Seconds between announcing a carving time and carving at it";
            type uint16 {
              range "1..60";
            }
            default 3;
            description
              "Seconds between announcing the carving instant and carving at
               it — RFC 7432 §8.5 step 2's peering timer, whose default of 3
               seconds RFC 9722 keeps. Larger values are worth having where
               BGP propagation is slow: an instant that arrives after it has
               passed is discarded, and that segment carves immediately.

               It also bounds what this PE will wait for: an announcement
               further ahead than this interval is rejected, so a peer with a
               skewed clock cannot park the election arbitrarily far out.";
          }
          leaf skew {
            ext:help "Milliseconds the outgoing DF steps down before the carving time";
            type uint16 {
              range "1..1000";
            }
            default 10;
            description
              "Milliseconds by which a PE **losing** the Designated Forwarder
               role steps down ahead of the announced instant; a PE gaining
               the role steps up at the instant itself (RFC 9722 §3.1).

               The asymmetry is deliberate: it guarantees the two never
               overlap, and pays for that with a skew-long window in which the
               bridge domain has no forwarder. On a bridged segment that is
               the right trade — a gap drops frames for that window, an
               overlap duplicates them and can loop. Raise it where
               forwarding-state programming is slow, but keep it well inside
               `peering-time`.";
          }
        }
        leaf dont-preempt {
          ext:help "Advertise the RFC 9785 Don't Preempt capability";
          type empty;
          description
            "Advertise the RFC 9785 §3 'Don't Preempt' (DP) capability bit in
             the DF Election extended community.

             On a preference **tie** a PE with the bit ranks ahead of one
             that does not set it; the comparison runs after the preference
             and before the originating address. It is a tie-break input on
             every PE of the segment, so a peer's bit is honoured whether or
             not this PE sets its own — ignoring it would make the two ends
             rank the segment differently and both would forward.

             The bit is defined for the preference-based algorithms and is
             advertised only under them.

             **This is the tie-break only, not non-revertive operation.**
             RFC 9785 §4.3 additionally has a recovering PE advertise an
             *operational* preference and DP inherited from the incumbent
             Designated Forwarder; that is not implemented. With the bit set
             on every PE at equal preference — the usual configuration — the
             tie still falls through to the address, so the lowest-address PE
             reclaims the role when it comes back.";
        }
        leaf ac-df {
          ext:help "Advertise the AC-Influenced DF election capability";
          type empty;
          description
            "Advertise the AC-DF (AC-Influenced DF election) capability bit
             in the DF Election extended community (RFC 8584 §2.2), telling
             the other PEs on the segment that this PE excludes itself from
             the election while its attachment circuit is down.

             Once every PE on the segment advertises it, the election for
             each EVI (each VPWS service instance, each bridge domain)
             counts only the PEs whose per-EVI Ethernet A-D route for it
             is present alongside their per-ES A-D (RFC 8584 §4.1). A PE
             whose attachment circuit for one EVI goes down withdraws that
             per-EVI A-D and drops out of that EVI's election alone — the
             other PEs re-elect at once, without the segment changing.
             Any PE without the capability keeps the whole segment on the
             plain Type-4 election.";
        }
        leaf startup-delay {
          ext:help "Seconds to stay out of the election after joining the segment";
          type uint16 {
            range "1..3600";
          }
          description
            "Seconds this PE stays out of the segment's Designated-Forwarder
             election after joining it — after the ESI is first configured,
             which on a reboot is when the startup configuration is applied.

             A PE that has just booted has not yet learned the other PEs'
             Type-4 routes. An election run against that empty candidate set
             elects this PE the DF for every service instance, so it starts
             forwarding toward a CE the incumbent DF is already serving and
             the CE sees duplicates. The hold gives BGP time to converge
             first.

             While the hold runs the PE suppresses this segment's ES routes
             (the Type-4 and the per-ES A-D) and advertises P=0/B=0 in the
             Layer-2 Attributes extended community of every VPWS service on
             the segment. Suppressing the advertisement is what makes the
             hold safe: deferring only the local election would leave the
             other PEs still seeing our Type-4 and still running the same
             deterministic election, free to hand the DF role to a PE that is
             refusing to forward.

             The corollary is that a segment with no other PE on it — a
             single-homed segment, or one whose peer is down — is down for
             the whole delay, since there is no incumbent for the hold to
             protect. That is why this is off by default.

             Unset = join the election immediately. Clearing it while a hold
             is running ends the hold at once. Interoperates with IOS-XR
             `timers peering`, Junos
             `designated-forwarder-election-hold-time` and FRR
             `evpn mh startup-delay`.";
        }
      }
    }
    list vpws {
      ext:help "EVPN VPWS point-to-point E-Line service (RFC 8214)";
      key "name";
      description
        "EVPN VPWS service (RFC 8214) — a point-to-point E-Line between one
         local attachment circuit and one remote PE's AC, no MAC learning.
         Advertises an Ethernet A-D per-EVI route (Type-1) whose Ethernet
         Tag is the local VPWS service instance id, carrying this PE's
         service binding per the afi-safi `encapsulation` — an End.DX2
         L2-Service Prefix-SID (RFC 9252 §6.3) under srv6, or the service
         VNI in the label field plus the VXLAN Encapsulation extended
         community (RFC 8365 §6) under vxlan; imports the remote's Type-1
         by matching its Ethernet Tag against remote-service-id and
         cross-connects the AC to the remote endpoint as the remote
         signalled it.";
      leaf name {
        ext:help "VPWS service name";
        type string;
        description "Operator-chosen VPWS service name (the list key).";
      }
      leaf evi {
        ext:help "EVPN Instance the service belongs to";
        type uint32 {
          range "1..16777215";
        }
        mandatory true;
        description
          "EVPN Instance the service belongs to — scopes the auto-derived
           RD (router-id:evi) and RT (AS:evi) both ends must share.";
      }
      leaf local-service-id {
        ext:help "Local VPWS service id (Type-1 Eth Tag)";
        type uint32;
        mandatory true;
        description
          "VPWS service instance id advertised as the Ethernet Tag of the
           local Type-1 route; the remote end configures this value as its
           remote-service-id.";
      }
      leaf remote-service-id {
        ext:help "Remote VPWS service id to match on Type-1";
        type uint32;
        mandatory true;
        description
          "Ethernet Tag expected on the remote PE's Type-1 route; a match
           binds the remote End.DX2 SID as this AC's cross-connect target.";
      }
      leaf interface {
        ext:help "Attachment circuit (CE-facing port) of the E-Line";
        type string;
        mandatory true;
        description "Attachment circuit (CE-facing port) of the E-Line.";
      }
      leaf mtu {
        ext:help "L2 MTU signalled on the Type-1 route (0 disables)";
        type uint16;
        default 0;
        description
          "L2 MTU signalled in the RFC 8214 §3.1 Layer-2 Attributes
           extended community on the Type-1 route. 0 disables the MTU
           check; when both ends signal non-zero MTUs that differ, the
           remote is not bound (the service shows mtu-mismatch).";
      }
      leaf vlan {
        ext:help "802.1Q VID scoping the attachment circuit";
        type uint16 {
          range "1..4094";
        }
        description
          "802.1Q VID scoping the attachment circuit (RFC 8214 VLAN-based
           E-Line): only tagged frames with this VID enter the
           cross-connect (the tag rides through the service), and the
           local SID becomes End.DX2V demuxed over the EVI's VLAN table.
           Absent = whole-port service (End.DX2).";
      }
      leaf vni {
        ext:help "VNI advertised for the service (default: the EVI)";
        type uint32 {
          range "1..16777215";
        }
        description
          "VXLAN Network Identifier advertised in the Type-1's label
           field under `encapsulation vxlan` (RFC 8365 §6) — the VNI the
           remote PE encapsulates this service's frames with, and this
           PE's decap identity for them. Absent = the EVI, the common
           fabric-wide-VNI deployment; set it when the VNI space is
           administered separately from the EVI space. Ignored under
           srv6.";
      }
      leaf ethernet-segment {
        ext:help "Override the Ethernet Segment inferred from the AC";
        type string;
        description
          "Name of an `ethernet-segment` this service's attachment circuit
           belongs to (RFC 8214 §5 multihoming). The referenced segment
           supplies the ESI carried in this service's Type-1 route and the
           redundancy mode that drives Designated-Forwarder election, run
           per <ESI, VPWS service instance> over the PEs advertising the
           segment's Type-4.

           Normally this is NOT needed: the segment is inferred from the
           attachment circuit, so an `ethernet-segment` whose `interface` is
           this service's `interface` binds automatically. Set this leaf
           only to override that — when several segments name the same
           access port, or when the segment declares no interface of its
           own. It always wins over inference; if it names a segment whose
           `interface` is some other port, the service still uses it and
           `show bgp evpn vpws` reports the discrepancy.

           No segment configured and none claiming the AC = single-homed:
           the Type-1 carries the all-zero ESI and is advertised as
           primary.";
      }
    }
    leaf bum-tunnel-type {
      ext:help "Inclusive BUM P-tunnel type (Type-3 PMSI)";
      type enumeration {
        enum ingress-replication {
          description
            "Ingress Replication (the default) — BUM is head-end
             replicated to each remote PE, optionally optimized by
             Assisted Replication per the `assisted-replication` role.";
        }
        enum sr-mpls-p2mp {
          description
            "SR-MPLS P2MP tree (PMSI tunnel type 0x0C) — BUM delivery is
             bound to an RFC 9524 replication tree rooted at this node.";
        }
        enum srv6-p2mp {
          description
            "SRv6 P2MP tree (PMSI tunnel type 0x0D) — the SRv6 form of
             the RFC 9524 replication tree.";
        }
      }
      default ingress-replication;
      description
        "Inclusive BUM P-tunnel advertised in the Type-3 IMET PMSI Tunnel
         attribute. The SR P2MP modes (draft-ietf-bess-mvpn-evpn-sr-p2mp)
         advertise a Tree-ID + Root identifier with the local node as the
         tree Root; they bypass Assisted Replication.";
    }
    container pruned-flood-list {
      ext:help "RFC 9574 Pruned-Flood-List pruning request";
      description
        "RFC 9574 Pruned-Flood-List: request that remote PEs prune this
         node from the named BUM flood categories by setting the matching
         flag in this node's Type-3 IMET PMSI Tunnel attribute. Honoring a
         received request is whole-VTEP only on a Linux VXLAN dataplane
         (one flood list per VNI), so a remote is dropped from the flood
         list only when it prunes BOTH categories.";
      leaf broadcast-multicast {
        ext:help "Prune from broadcast/multicast flood list";
        type boolean;
        default false;
        description
          "Ask peers to prune this node from the broadcast/multicast flood
           list (RFC 9574 BM flag).";
      }
      leaf unknown-unicast {
        ext:help "Prune from unknown-unicast flood (U flag)";
        type boolean;
        default false;
        description
          "Ask peers to prune this node from the unknown-unicast flood
           list (RFC 9574 U flag).";
      }
    }
    container assisted-replication {
      ext:help "Assisted Replication role (RFC 9574)";
      description
        "RFC 9574 Optimized Ingress Replication (Assisted Replication)
         role for the local speaker. Applies to every VNI advertised
         under `advertise-all-vni`.";
      leaf role {
        ext:help "Assisted Replication role for this speaker";
        type enumeration {
          enum none {
            description
              "Regular NVE — plain ingress replication (the default).";
          }
          enum replicator {
            description
              "AR-REPLICATOR — advertise a Replicator-AR Type-3 route
               (PMSI tunnel type 0x0A) whose next hop is `replicator-ip`,
               so AR-LEAF nodes offload BUM replication here.";
          }
          enum leaf {
            description
              "AR-LEAF — tag the Regular-IR Type-3 route as AR-LEAF and
               offload BUM replication to an AR-REPLICATOR.";
          }
        }
        default none;
        description
          "Assisted Replication role advertised in the Type-3 IMET PMSI
           Tunnel attribute (RFC 9574 §4, the T field).";
      }
      leaf replicator-ip {
        ext:help "AR-IP address advertised by an AR-REPLICATOR";
        type inet:ip-address;
        description
          "The AR-IP — a distinct routable local address advertised in
           the Replicator-AR route's next hop and used as the BUM tunnel
           destination by AR-LEAF nodes. Required when `role` is
           `replicator`; ignored otherwise.";
      }
      leaf selective {
        ext:help "Enable Selective Assisted Replication (RFC 9574)";
        type boolean;
        default false;
        description
          "Selective Assisted Replication (RFC 9574). When true on an
           AR-REPLICATOR, its Replicator-AR route carries the L (Leaf
           Information Required) flag, soliciting Leaf A-D routes (EVPN
           Route Type 11) so the replicator learns exactly which AR-LEAFs
           to replicate to. An AR-LEAF originates a Leaf A-D toward each
           selective replicator it sees. Non-selective (the default)
           replicates to every node in the broadcast domain.";
      }
    }
    container etree {
      ext:help "EVPN E-Tree: root and leaf attachment circuits (RFC 8317)";
      description
        "EVPN E-Tree (RFC 8317): every attachment circuit is a root or a
         leaf, and a leaf may not reach another leaf. An AC not listed
         as a leaf is a root, so a PE with no leaf ACs needs no E-Tree
         configuration. Needs the cradle data plane (`system ebpf
         enabled` or `system cradle enabled`): a commit without it is
         refused, because the kernel bridge cannot isolate leaves (a
         startup config is only warned about).

         Enforced by cradle on the ports it has attached: leaf to leaf on
         one PE, and known unicast from a leaf to a MAC behind a leaf on
         another PE. A leaf's broadcast, multicast and unknown unicast
         are kept from leaves on other PEs too: over MPLS by a leaf label
         (RFC 8317 §4.2), over SRv6 by a leaf argument of the End.DT2M
         SID (RFC 9819), and over VXLAN by the IMET of a PE whose ACs are
         all leaves, which is not exact between two PEs that each have
         both roots and leaves. A leaf the kernel bridge switches
         instead (cradle has not attached it yet) is isolated from the
         other leaves there, and held in the listening state until cradle
         has it.";
      list leaf-interface {
        ext:help "A leaf attachment circuit";
        key "name";
        description
          "A leaf AC, by interface name: the bridge port the CE is
           attached to (for a multihomed CE, the Ethernet Segment's
           interface). MACs learned on it are advertised with the E-Tree
           community's Leaf-Indication flag (RFC 8317 §4.1), and the
           cradle data plane keeps it from every other leaf.";
        leaf name {
          ext:help "Interface name";
          type string;
        }
      }
    }
  }

  /* =========================================================
   * Augments into the zebra-rs configure tree
   * ========================================================= */

  augment "/configure:set/config:router/bgp:bgp/bgp:afi-safi" {
    description
      "Attach the EVPN extension leaves to the global afi-safi list
       in the candidate-set subtree.";
    uses bgp-afi-safi-evpn-extension;
  }

  augment "/configure:delete/config:router/bgp:bgp/bgp:afi-safi" {
    description
      "Same attachment for the delete subtree so
       `delete router bgp afi-safi evpn advertise-all-vni`
       is path-valid.";
    uses bgp-afi-safi-evpn-extension;
  }
}

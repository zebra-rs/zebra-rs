module zebra-rib-tracing {
  yang-version "1";

  namespace "urn:ietf:params:xml:ns:yang:zebra-rib-tracing";
  prefix "zrft";

  import config {
    prefix config;
  }

  import configure {
    prefix configure;
  }

  import extension {
    prefix ext;
  }

  organization
    "zebra-rs";

  contact
    "https://github.com/zebra-rs";

  description
    "Conditional tracing for the central RIB and the FIB dataplane,
     attached under the top-level `system` container:

       system {
         tracing { ... }
       }

     The RIB instance owns both the routing tables and the netlink
     FIB handle in one task, so there is a single scope here (unlike
     the BGP block's instance / per-neighbor split). The block is
     divided by plane to mirror the operator's mental model and the
     Juniper `routing-options` (RIB) vs `forwarding-options` (FIB)
     traceoptions split:

       * `tracing rib { ... }` — the control-plane RIB: route
         add/withdraw and best-path selection, recursive nexthop
         resolution / Next-Hop Tracking, redistribution to and from
         protocol clients, MPLS ILM, static-route processing,
         interface / connected-address handling, VRF lifecycle, and
         SRv6 SID resolution.
       * `tracing fib { ... }` — the dataplane: what is programmed
         into the kernel over netlink (routes, nexthop groups, the
         raw southbound messages in either direction, the MPLS LFIB,
         the ARP / ND neighbor table, interface / address programming,
         link master-binding (bridge enslavement), VRF devices, SRv6
         `seg6local` SIDs, and L2 / EVPN objects (bridge, VXLAN, FDB,
         MDB)).

     The category set was derived by cataloguing every existing
     `tracing::` site in `src/rib` and `src/fib` and giving each a
     home; genuine error-level `warn!` sites stay unconditional, so a
     category gates only the verbose informational traces beside
     them.

     `route` and `nexthop` deliberately appear on both planes: it is
     the single most useful split this block buys you — a route can
     be resolved and best in the RIB yet never make it into the
     kernel, and only side-by-side `rib route` + `fib route` traces
     show where it stalled.

     This follows the same gated-macro design as the IS-IS / OSPF /
     BGP `tracing` blocks: a typed config struct consulted by log
     macros, so categories turn on at runtime without a rebuild.

     Example:

       system {
         tracing {
           rib {
             route { detail; }   // route churn, fully decoded
             nexthop;            // resolution + NHT, summary
           }
           fib {
             route;                          // kernel route program
             kernel { direction receive; }   // only events FROM the kernel
           }
         }
       }

     Each leaf is a presence flag — name it to enable, delete it to
     disable; absence means the category is silent. Enabling by
     presence (rather than a `true` value) matches the IS-IS / OSPF /
     BGP `tracing` blocks: the config callbacks key off set vs delete
     and never read a value, so `type empty` is the honest type.";

  revision 2026-07-29 {
    description
      "Add the `config` block — categories for the configuration
       subsystem itself, applied by the config manager synchronously
       at commit time rather than via a subscriber task. `config
       startup` gates the startup-config apply summary (`applied N of
       M commands`), which previously logged unconditionally; because
       the toggle is applied before the summary is emitted, it can be
       carried in the very startup file whose application it traces.
       Failure outcomes (missing / empty / unreadable / rejected
       startup config) stay unconditional: they fire only when the
       config file carries no commands, so a config-borne toggle could
       never have enabled them. `config vty` gates the VTY session
       lifecycle / RPC traces (formerly behind the compile-time
       VTY_TRACING const); the one-shot serve() setup notices fire
       before the startup config is loaded and log at debug level
       instead. The `all` master switch covers the new block.";
  }

  revision 2026-07-07 {
    description
      "Add the top-level `task` category — gates daemon task
       spawn / despawn lifecycle traces (the BGP per-VRF task spawn /
       Shutdown logs and the RIB subscribe-race warning that
       accompanies a respawn) that previously logged unconditionally.
       Unlike `rib` / `fib`, `task` is a cross-cutting category rather
       than a forwarding plane.";
  }

  revision 2026-06-19 {
    description
      "Add the `fib link` category — gates the link master-binding
       traces (bridge enslavement / `link_set_master` and the
       deferred-bind bookkeeping) that previously logged
       unconditionally.";
  }

  revision 2026-06-05 {
    description
      "Initial revision — `system tracing` block split into a `rib`
       plane (route, nexthop, redistribute, label, static, interface,
       vrf, srv6) and a `fib` plane (route, nexthop, kernel, label,
       neighbor, interface, vrf, srv6, l2{bridge,vxlan,fdb,mdb}), plus
       an `all` master switch. The verbose categories (route, nexthop,
       interface, srv6 on each plane, plus `fib kernel`) are presence
       containers carrying an optional `detail`; `fib kernel`
       additionally takes a `direction` (send|receive; omit for
       both). The category set covers every existing trace site in
       src/rib and src/fib.";
  }

  grouping rib-tracing-detail-option {
    description
      "The `detail` refinement shared by the verbose presence-container
       toggles (`rib route` / `nexthop` / `interface` / `srv6`,
       `fib route` / `nexthop` / `kernel` / `interface` / `srv6`). The
       enclosing container's presence is what enables tracing for that
       category; `detail` only widens each event from a one-line
       summary to a fully decoded record.";

    leaf detail {
      ext:help "Log the fully decoded entry, not just a one-line summary";
      type empty;
      description
        "When present, log the complete entry (all prefixes /
         nexthops / flags / encap) instead of a one-line summary.";
    }
  }

  grouping rib-tracing-extension {
    description
      "The `tracing` block grafted under `system`. Kept in a grouping
       so the candidate-`set` and `delete` subtrees stay identical by
       construction.";

    container tracing {
      ext:help "RIB / FIB conditional tracing";
      description
        "Per-category RIB and FIB log toggles, grouped by plane.";

      leaf all {
        ext:help "Enable every tracing category";
        type empty;
        description
          "Master switch — when present, every tracing category is
           traced regardless of its individual leaf: `task` and
           everything under `config`, `rib` and `fib`.";
      }

      leaf task {
        ext:help "Trace daemon task spawn / despawn lifecycle";
        type empty;
        description
          "Log daemon task spawn / despawn lifecycle. Covers the BGP
           per-VRF tasks — task spawn (with its RD / router-id / table /
           label / SID summary), the `Shutdown` sent on despawn, and the
           RIB subscribe race that surfaces when a task is respawned
           before its earlier subscribe delivered its dump — and the
           OSPF / OSPFv3 per-VRF instance spawn / despawn. Unlike `rib`
           and `fib`, this is a cross-cutting category, not tied to a
           single forwarding plane.";
      }

      container config {
        ext:help "Trace configuration subsystem processing";
        description
          "Categories for the configuration subsystem itself. Unlike
           `rib` / `fib`, these toggles are applied by the config
           manager synchronously at commit time (not via a subscriber
           task), so a toggle carried in the startup config file is
           live before the startup summary it gates is emitted.";

        leaf startup {
          ext:help "Trace the startup config apply summary";
          type empty;
          description
            "Log the startup-config success summary — resolved path,
             detected format, and `applied N of M commands` — after
             the startup commit. Failure outcomes (unreadable file,
             per-command rejections, schema-rejected commit) are
             logged unconditionally at error level regardless of this
             toggle; the empty-file and missing-file notes are also
             unconditional, since a boot that hits them had no config
             that could have carried the toggle.";
        }

        leaf vty {
          ext:help "Trace VTY session lifecycle and RPC events";
          type empty;
          description
            "Log VTY session lifecycle and per-RPC events: session
             creation on first RPC, per-RPC accept, logout / disable,
             enable promotion (root noop, config-group, PAM success),
             session removal when the client shell exits, and GC
             sweeps that removed sessions. Denied RPCs and
             authentication failures are warnings and always logged
             regardless of this toggle. The one-shot serve() setup
             notices (listening socket, configure-authorization group,
             peer allow-list, GC start) fire before the startup config
             is loaded, so they are debug-level rather than gated
             here.";
        }
      }

      container rib {
        ext:help "Trace control-plane RIB processing";
        description
          "Control-plane RIB categories: route table changes,
           recursive nexthop resolution, client redistribution,
           MPLS ILM, static-route processing, interface /
           connected-address handling, VRF lifecycle, and SRv6 SID
           resolution.";

        container route {
          ext:help "Trace route add / withdraw and best-path selection";
          presence "Trace RIB route changes";
          description
            "Log IPv4 / IPv6 route add and withdraw into the RIB and
             the best-path selection among competing entries for a
             prefix (administrative distance / metric resolution).";
          uses rib-tracing-detail-option;
        }
        container nexthop {
          ext:help "Trace nexthop resolution and Next-Hop Tracking";
          presence "Trace RIB nexthop resolution";
          description
            "Log recursive nexthop resolution and Next-Hop Tracking
             (NHT) register / notify — the reachability gating that
             decides whether a route's nexthop is usable.";
          uses rib-tracing-detail-option;
        }
        leaf redistribute {
          ext:help "Trace route exchange with protocol clients";
          type empty;
          description
            "Log routes exchanged with protocol clients (BGP / IS-IS /
             OSPF) through the RIB client registry — both what clients
             redistribute in and what the RIB notifies back out.";
        }
        leaf label {
          ext:help "Trace MPLS ILM handling in the RIB";
          type empty;
          description
            "Log MPLS ILM (incoming-label-map) handling in the RIB:
             local-label allocation and label-to-nexthop bindings.";
        }
        leaf static {
          ext:help "Trace static-route processing";
          type empty;
          description
            "Log static-route configuration processing — how
             configured static routes are resolved and handed to the
             RIB.";
        }
        container interface {
          ext:help "Trace interface / connected-address handling";
          presence "Trace RIB interface and connected-address events";
          description
            "Log link-table and connected-address handling: link
             up / down transitions, MTU changes, and connected-route
             recovery (re-installing configured addresses the kernel
             dropped, with the external-actor flap suppression that
             guards it).";
          uses rib-tracing-detail-option;
        }
        leaf vrf {
          ext:help "Trace VRF lifecycle";
          type empty;
          description
            "Log VRF lifecycle in the RIB: VRF add / delete (including
             adoption of an existing kernel VRF), per-VRF table
             allocation, and interface-to-VRF binding (deferred until
             both the link and the VRF are present).";
        }
        container srv6 {
          ext:help "Trace SRv6 SID resolution";
          presence "Trace RIB SRv6 SID handling";
          description
            "Log SRv6 SID handling in the RIB: End / End.X / End.DT
             SID resolution (behavior, locator, owner, SID device
             ifindex, nexthop) before the SID is programmed into the
             FIB. Distinct from `label`, which is MPLS-only.";
          uses rib-tracing-detail-option;
        }
      }

      container fib {
        ext:help "Trace FIB dataplane programming";
        description
          "Dataplane categories: what is programmed into the kernel
           over netlink — routes, nexthop groups, the raw southbound
           messages, the MPLS LFIB, the ARP / ND table, interface /
           address programming, link master-binding (bridge
           enslavement), VRF devices, SRv6 `seg6local` SIDs, and L2 /
           EVPN objects (bridge, VXLAN, FDB, MDB).";

        container route {
          ext:help "Trace route programming to the kernel";
          presence "Trace FIB route programming";
          description
            "Log route programming to the kernel FIB over netlink
             (route add / delete as the RIB's best paths are
             installed and withdrawn).";
          uses rib-tracing-detail-option;
        }
        container nexthop {
          ext:help "Trace nexthop-group programming to the kernel";
          presence "Trace FIB nexthop-group programming";
          description
            "Log nexthop-group programming to the kernel FIB — the
             shared nexthop objects that installed routes reference.";
          uses rib-tracing-detail-option;
        }
        container kernel {
          ext:help "Trace raw netlink messages on the southbound socket";
          presence "Trace raw netlink messages";
          description
            "Log raw netlink messages on the southbound socket. With
             no `direction`, both are traced: `send` is what zebra-rs
             programs into the kernel, `receive` is what the kernel
             reports back (link up / down, address changes, and routes
             owned by other daemons).";
          uses rib-tracing-detail-option;
          leaf direction {
            ext:help "Restrict tracing to a single netlink direction";
            type enumeration {
              enum send {
                description "Trace only messages programmed to the kernel.";
              }
              enum receive {
                description "Trace only messages received from the kernel.";
              }
            }
            description
              "Limit tracing to one netlink direction. Omit to trace
               both — there is no explicit `both` value; absence means
               both.";
          }
        }
        leaf label {
          ext:help "Trace MPLS LFIB programming to the kernel";
          type empty;
          description
            "Log MPLS LFIB programming to the kernel — ILM entries
             (label swap / pop / php) pushed over netlink.";
        }
        leaf neighbor {
          ext:help "Trace ARP / ND neighbor table programming";
          type empty;
          description
            "Log ARP / ND (IPv4 / IPv6 neighbor) table programming to
             the kernel.";
        }
        container interface {
          ext:help "Trace interface / address programming to the kernel";
          presence "Trace FIB interface and address programming";
          description
            "Log interface and connected-address programming to the
             kernel: link admin up, MTU set, dummy-device create /
             delete, and address add / delete over netlink.";
          uses rib-tracing-detail-option;
        }
        leaf link {
          ext:help "Trace link enslavement / master binding to the kernel";
          type empty;
          description
            "Log link master-binding programming: enslaving an interface
             to a bridge master over netlink (`link_set_master`), plus the
             deferred-bind bookkeeping that holds the bind pending until
             both the slave interface and the bridge device appear.";
        }
        leaf vrf {
          ext:help "Trace VRF device programming to the kernel";
          type empty;
          description
            "Log VRF dataplane programming: VRF device create / delete
             and enslaving an interface to a VRF master over netlink.";
        }
        container srv6 {
          ext:help "Trace SRv6 SID programming to the kernel";
          presence "Trace FIB SRv6 SID programming";
          description
            "Log SRv6 SID programming to the kernel: End-behavior
             `seg6local` routes (install / uninstall) and the SID
             device they point at. Distinct from `label`, which is
             the MPLS LFIB.";
          uses rib-tracing-detail-option;
        }
        container l2 {
          ext:help "Trace L2 / EVPN dataplane programming";
          description
            "Log L2 / EVPN dataplane programming to the kernel. Each
             leaf is an independent presence toggle; the EVPN control
             plane itself is out of scope here — this covers only what
             the FIB pushes over netlink.";

          leaf bridge {
            ext:help "Trace bridge device programming";
            type empty;
            description
              "Log bridge-device create / delete and address-
               generation-mode changes.";
          }
          leaf vxlan {
            ext:help "Trace VXLAN device programming";
            type empty;
            description
              "Log VXLAN-device create / delete and address-
               generation-mode changes, plus VNI-to-ifindex
               registration.";
          }
          leaf fdb {
            ext:help "Trace MAC / FDB entry programming";
            type empty;
            description
              "Log bridge FDB programming: MAC add / delete (including
               ESI / EVPN-sourced entries) over netlink.";
          }
          leaf mdb {
            ext:help "Trace multicast (MDB) entry programming";
            type empty;
            description
              "Log multicast forwarding database (MDB) add / delete
               over netlink.";
          }
        }
      }
    }
  }

  /* =========================================================
   * Augments into the zebra-rs configure tree
   * ========================================================= */

  augment "/configure:set/config:system" {
    description
      "`system tracing` in the candidate-set subtree.";
    uses rib-tracing-extension;
  }

  augment "/configure:delete/config:system" {
    description
      "Same attachment for the delete subtree so
       `delete system tracing ...` is path-valid.";
    uses rib-tracing-extension;
  }
}

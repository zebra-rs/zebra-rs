module zebra-bgp-transport {
  yang-version "1";

  namespace "urn:ietf:params:xml:ns:yang:zebra-bgp-transport";
  prefix "zbt";

  import ietf-inet-types {
    prefix inet;
    reference "RFC 6991: Common YANG Data Types.";
  }

  import ietf-bgp {
    prefix bgp;
  }

  import config {
    prefix config;
  }

  import configure {
    prefix configure;
  }

  import extension {
    prefix ext;
  }

  organization
    "zebra-rs";

  contact
    "https://github.com/zebra-rs";

  description
    "FRR-style flat per-neighbor transport extensions on the BGP
     candidate-config tree.

     Adds `update-source` directly under each BGP neighbor so the
     CLI shape matches FRR / IOS:

       router bgp {
         neighbor 10.0.0.5 {
           remote-as 65501;
           update-source 10.0.0.1;
         }
       }

     Functionally equivalent to the IETF YANG path
     `neighbor/transport/local-address` (ietf-bgp-common@2023-07-05);
     both lower onto the same runtime field
     (`peer.config.transport.update_source`) and the same TCP-bind
     site in `peer_connect`. Operators using the FRR vocabulary get
     the flat form without giving up the IETF tree.";

  revision 2026-06-12 {
    description
      "Add per-neighbor `ip-transparent` (presence container): set
       IP_TRANSPARENT / IPV6_TRANSPARENT on the neighbor's TCP socket
       so the session can use a local address the host does not own
       (paired with `update-source`).";
    reference
      "FRR 10.4 `neighbor X ip-transparent` (FRRouting/frr PR #18789).";
  }

  revision 2026-06-09 {
    description
      "Add per-neighbor `port <1-65535>` (TCP destination port used to
       dial the neighbor, default 179) and instance-level
       `port <0-65535>` (TCP port the BGP listener binds; 0 disables
       listening entirely, default 179).";
    reference
      "FRR `neighbor X port (0-65535)`; FRR bgpd `-p/--bgp_port`
       startup option (port 0 sets BGP_OPT_NO_LISTEN).";
  }

  revision 2026-06-08 {
    description
      "Add `tcp-mss <1-65535>` per-neighbor leaf (TCP_MAXSEG clamp), and
       `disable-connected-check`: let a single-hop eBGP session reach a
       peer that is not on a directly-connected subnet (e.g. loopback
       peering across one L2 hop) without raising the TTL.";
    reference
      "FRR `neighbor X tcp-mss <N>`; FRR `neighbor X disable-connected-check`.";
  }

  revision 2026-05-05 {
    description "Initial revision.";
    reference "FRR `neighbor X update-source`; Cisco IOS equivalent.";
  }

  grouping bgp-neighbor-transport-extension {
    description
      "FRR-style transport leaves on a BGP neighbor.";

    leaf update-source {
      ext:help "Source address to bind for outbound BGP TCP connect";
      type union {
        type inet:ipv4-address;
        type inet:ipv6-address;
      }
      description
        "Local IP address (IPv4 or IPv6) to bind before the outbound
         BGP TCP connect to this neighbor. The address family must
         match the peer's address family. When absent, the kernel
         picks the source via the routing table.

         Equivalent to `neighbor X update-source` in FRR / Cisco
         IOS, and to `neighbor/transport/local-address` in
         ietf-bgp-common.";
    }

    container ttl-security {
      ext:help "Enable GTSM: require directly-connected peer (TTL 255)";
      presence "Enable GTSM (TTL 255 send + receive enforcement) for this neighbor";
      description
        "When present, enable the Generalized TTL Security Mechanism
         (GTSM) for this neighbor. The peer is treated as directly
         connected (single hop): every BGP packet is sent with IP TTL
         / IPv6 Hop Limit = 255, and inbound packets are accepted only
         when their received TTL / Hop Limit is 255 (enforced by the
         kernel via IP_MINTTL / IPV6_MINHOPCOUNT). A packet that has
         crossed at least one router arrives with TTL < 255 and is
         dropped before it reaches BGP, which protects the session
         from off-path spoofing.

         This node is a flag (presence container), not a hop count: the only
         supported policy is the directly-connected case (expected hop
         count 0, TTL 255). A configurable number of hops, as in
         `neighbor X ttl-security hops <N>`, is intentionally not
         supported. Mutually exclusive with ebgp-multihop, which permits
         the TTL to be decremented between peers: configuring both on one
         neighbor is rejected (the second is refused with a warning).";
      reference
        "RFC 3682: The Generalized TTL Security Mechanism (GTSM).
         RFC 5082: GTSM (obsoletes RFC 3682).
         RFC 7454: BGP Operations and Security, Section 6.";
    }

    leaf ebgp-multihop {
      ext:help "Allow an eBGP peer up to N hops away (TTL 1-255)";
      type uint8 {
        range "1..255";
      }
      description
        "Maximum number of hops to an eBGP neighbor — the egress IP TTL
         / IPv6 Hop Limit used for the session. A directly-connected
         eBGP peer uses TTL 1 by default and is unreachable through a
         router; setting `ebgp-multihop N` raises the egress TTL to N so
         a peer up to N hops away (for example peering on loopbacks
         across one or more routers) can be reached.

         Ignored for iBGP, which already uses 255. Mutually exclusive
         with ttl-security, which pins the TTL to 255 and additionally
         filters the received TTL: configuring both on one neighbor is
         rejected — the config callback refuses the second with a warning
         and the first-configured one wins, so remove one before adding
         the other.

         Equivalent to `neighbor X ebgp-multihop <N>` in FRR / Cisco
         IOS, and to `neighbor/transport/ebgp-multihop/multihop-ttl` in
         ietf-bgp-common.";
      reference
        "RFC 4271: A Border Gateway Protocol 4 (BGP-4).";
    }

    leaf tcp-mss {
      ext:help "Cap the TCP MSS for this neighbor (1-65535)";
      type uint16 {
        range "1..65535";
      }
      description
        "TCP Maximum Segment Size (`setsockopt(TCP_MAXSEG)`) for this
         neighbor's session, in bytes. Bounds the size of every BGP
         segment so the session stays under a path MTU smaller than the
         interface MTU — a tunnel, an MPLS core, or a link that cannot
         carry full-size frames — avoiding a stall on a black-holed
         large UPDATE.

         The value is applied to the socket *before* the TCP handshake:
         on the active connect socket (so the SYN advertises the clamp)
         and on the listening socket (so a passively-accepted connection
         inherits it). Because a listening socket carries a single value
         for all peers, the daemon installs the minimum `tcp-mss` across
         the configured peers of each address family on the listener,
         matching FRR; the active path applies each peer's own value
         exactly.

         Changing `tcp-mss` does not bounce a live session: the new value
         takes effect on the next connect, so reset the session
         (`clear bgp <peer>`) to apply it immediately. `show bgp neighbor`
         reports both the configured value and the MSS the kernel actually
         negotiated (the *synced* value), which the kernel may set a little
         below the configured one (it subtracts per-segment TCP options).

         Equivalent to `neighbor X tcp-mss <N>` in FRR / Cisco IOS, and to
         `neighbor/transport/tcp-mss` in ietf-bgp-common.";
      reference
        "RFC 879: The TCP Maximum Segment Size and Related Topics.
         RFC 4271: A Border Gateway Protocol 4 (BGP-4).";
    }

    leaf port {
      ext:help "TCP port to dial this neighbor (default 179)";
      type uint16 {
        range "1..65535";
      }
      description
        "TCP destination port this router dials when it actively opens
         the BGP session toward this neighbor. When absent, the IANA
         default of 179 is used; deleting the leaf returns to 179.

         Only the active (outgoing) connection is affected: an inbound
         connection is matched to its neighbor by source address alone,
         never by port, so this leaf does not change what the local
         listener accepts. To move the local listening side off 179,
         set the instance-level `router bgp port` instead — the usual
         pairing is `port <N>` on the instance of one router and
         `neighbor X port <N>` on the router that dials it.

         A change (set, change, or delete) on a session that is already
         up bounces it — the same teardown `clear bgp ... hard` uses —
         so the session re-establishes on the new port immediately
         (FRR's `peer_change_reset` behaviour for this knob).

         Equivalent to `neighbor X port` in FRR / Cisco IOS.";
      reference
        "RFC 4271: A Border Gateway Protocol 4 (BGP-4), Section 8
         (TCP port 179).";
    }

    container ip-transparent {
      ext:help "Bind a local address the host does not own";
      presence "Set IP_TRANSPARENT on this neighbor's TCP socket";
      description
        "When present, set the IP_TRANSPARENT (IPv4) / IPV6_TRANSPARENT
         (IPv6) socket option on this neighbor's TCP socket. The option
         lets the session bind to — and emit packets from — a local
         address that is not configured on the host: normally the kernel
         rejects a bind() to a non-local address and refuses a non-local
         source on output; IP_TRANSPARENT (which requires CAP_NET_ADMIN)
         bypasses both checks. The source address itself comes from
         `update-source`, so the two are used together: update-source
         names the address the host does not own, ip-transparent makes
         the kernel accept it. On the active connect path the option is
         applied only when `update-source` is also configured (matching
         FRR); without it there is nothing for the option to liberate.
         The option is also folded onto the BGP listening sockets while
         any neighbor of that address family has it, so a passively
         accepted session destined to a non-local address (e.g. one
         steered to the daemon with TPROXY-style policy routing) can be
         answered.

         Typical uses: running bgpd in a container that peers as a
         loopback address not plumbed inside that netns; hitless
         takeover of a keepalived/VRRP virtual IP (pre-bind on the
         standby, establish instantly after failover); a
         bump-in-the-wire box terminating BGP with addresses owned by
         the devices around it.

         The option only liberates the local socket — the operator must
         still arrange for return traffic destined to the non-local
         address to reach the daemon (an AnyIP-style `ip route add
         local … dev lo`, TPROXY/fwmark policy routing, or — for a VIP —
         the peer simply not routing here until the VIP is owned).

         A change on a live session bounces it (FRR `peer_change_reset`):
         the option must be on the socket before bind()/connect(), so
         only a reconnect can apply it.";
      reference
        "FRR 10.4 `neighbor X ip-transparent` (FRRouting/frr PR #18789).
         Linux ip(7) IP_TRANSPARENT; ipv6(7) IPV6_TRANSPARENT.";
    }

    container disable-connected-check {
      ext:help "Allow a single-hop eBGP peer off-subnet";
      presence "Skip the directly-connected-network check for this eBGP neighbor";
      description
        "When present, skip the directly-connected-network check for this
         eBGP neighbor.

         By default a single-hop eBGP session (egress TTL 1, i.e. no
         ebgp-multihop and no ttl-security) is only brought up when the
         neighbor's address sits on one of the router's directly-connected
         subnets. This is the standard safety behaviour: an eBGP peer is
         expected to be one hop away. A session toward an address reachable
         only through a static or learned route — most commonly a peer's
         loopback — is therefore held down.

         `disable-connected-check` removes that requirement while leaving
         the egress TTL at 1. The intended topology is two routers that are
         directly connected at layer 2 but peer using addresses (typically
         loopbacks) that are not on the shared subnet: a TTL-1 packet still
         reaches the neighbor because no router decrements it, so raising
         the TTL with ebgp-multihop is unnecessary and would only weaken
         the single-hop guarantee.

         Enable it on the end(s) that dial the non-connected address. The
         check applies to eBGP only; iBGP, ebgp-multihop and ttl-security
         sessions are never gated by it, so the knob is a no-op there.

         Equivalent to `neighbor X disable-connected-check` in FRR / Cisco
         IOS (FRR also accepts the legacy spelling `enforce-multihop`).";
      reference
        "RFC 4271: A Border Gateway Protocol 4 (BGP-4).";
    }
  }

  grouping bgp-instance-transport-extension {
    description
      "FRR-style transport leaves on the BGP instance itself.";

    leaf port {
      ext:help "TCP listen port (0-65535; 0 disables, default 179)";
      type uint16 {
        range "0..65535";
      }
      description
        "TCP port the BGP server socket listens on for inbound
         sessions (IPv4 and IPv6 listeners both). When absent, the
         IANA default of 179 is used; deleting the leaf returns to
         179. The special value 0 disables listening entirely: the
         server sockets are closed and no inbound BGP connection can
         be accepted — every session must then be opened actively by
         this router.

         Changing the value closes the current listeners and reopens
         them on the new port (or, for 0, just closes them). Sessions
         that are already established are not touched — only the
         listening socket cycles; a remote peer that later dials the
         old port is refused by the kernel.

         Outgoing connections are unaffected: they go to each
         neighbor's default or configured `neighbor X port`, and the
         local source port of a dialed session stays ephemeral.

         Scope is this instance's listener (the default VRF task);
         per-VRF instances keep the default port.

         FRR exposes this only as the `-p/--bgp_port` startup option
         (0 likewise meaning do-not-listen); here it is runtime
         configuration.";
      reference
        "RFC 4271: A Border Gateway Protocol 4 (BGP-4), Section 8
         (TCP port 179).";
    }
  }

  /* =========================================================
   * Augments into the zebra-rs configure tree
   * ========================================================= */

  augment "/configure:set/config:router"
        + "/bgp:bgp/bgp:neighbor" {
    description
      "Attach update-source to BGP neighbors in the candidate-set
       subtree.";
    uses bgp-neighbor-transport-extension;
  }

  augment "/configure:delete/config:router"
        + "/bgp:bgp/bgp:neighbor" {
    description
      "Same attachment for the delete subtree so
       `delete router bgp neighbor X update-source` is path-valid.";
    uses bgp-neighbor-transport-extension;
  }

  augment "/configure:set/config:router"
        + "/bgp:bgp" {
    description
      "Attach the instance-level transport leaves (listen `port`) in
       the candidate-set subtree.";
    uses bgp-instance-transport-extension;
  }

  augment "/configure:delete/config:router"
        + "/bgp:bgp" {
    description
      "Same attachment for the delete subtree so
       `delete router bgp port` is path-valid.";
    uses bgp-instance-transport-extension;
  }
}

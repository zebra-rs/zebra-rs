module configure {
  yang-version "1";

  namespace "urn:ietf:params:xml:ns:yang:zebra";
  prefix "configure";

  import ietf-inet-types {
    prefix inet;
  }

  import extension {
    prefix ext;
  }

  import dhcp {
    prefix dhcp;
  }

  import config {
    prefix config;
  }

  import iana-bgp-community-types {
    prefix bct;
    reference
      "RFC XXXX: YANG Model for Border Gateway Protocol (BGP-4).";
  }

  import zebra-bgp-clear {
    prefix zbc;
  }

  import zebra-bgp-neighbor-group {
    prefix zbng;
  }

  import zebra-ipv6-router-advertisements {
    prefix zird;
  }

  import zebra-bgp-interface-neighbor {
    prefix zbin;
  }

  import zebra-bgp-dynamic-neighbors {
    prefix zbdn;
  }

  container set {
    ext:help "Set configuration";
    uses "config:config";
  }

  container delete {
    ext:help "Delete configuration";
    uses "config:config";
  }

  leaf exit {
    ext:help "Change to configure mode";
    type empty;
  }

  leaf help {
    ext:help "Show help";
    type empty;
  }

  // `running`, `candidate`, `json`, `yaml`, `diff`, `list` were removed
  // in favor of the unified `show candidate-config { formal | json |
  // yaml }` and `show running-config { formal | json | yaml }` trees
  // defined under the `show` container in exec.yang (and grafted into
  // configure mode). See book/src/ch-06-02-show-config-commands.md.

  leaf commit {
    ext:help "Commit candidate config to running config";
    type empty;
  }

  leaf discard {
    ext:help "Discard candidate config";
    type empty;
  }

  leaf load {
    ext:help "Load config from file";
    type empty;
  }

  // `save` alone writes the running config in whatever format the
  // config file is already in (see `ConfigManager::config_format`); a
  // format keyword writes that format instead and makes it the file's
  // format from then on. Modeled as a presence container — the same
  // shape `show running-config { formal | json | yaml }` uses in
  // exec.yang — so the bare command stays a valid terminal.
  container save {
    ext:help "Save config to file";
    presence "Save in the config file's current format";
    leaf cli {
      ext:help "Cisco-style indented block format";
      type empty;
    }
    leaf formal {
      ext:help "Set-style flat statement listing";
      type empty;
    }
    leaf json {
      ext:help "Pretty-printed JSON";
      type empty;
    }
    leaf yaml {
      ext:help "YAML";
      type empty;
    }
  }

  container clear {
    ext:help "Clear operational state";
    container isis {
      ext:help "IS-IS clear actions";
      // Force-recalculate the IS-IS SPF instead of waiting for the
      // next LSDB update or the debounce timer. Useful when manual
      // diagnosis suspects a stuck route after an LSDB-side fix.
      //
      // Modeled as a presence list so the bare `clear isis spf` is a
      // valid terminal (-> recalculate both L1 and L2) yet still
      // accepts an optional `level-1`/`level-2` key (-> recalculate
      // just that level), the same shape as `clear ospf neighbor
      // [<router-id>]`.
      list spf {
        ext:help "Force SPF recalculation (bare does both levels)";
        ext:presence "Recalculate both L1 and L2 SPF";
        key level;
        leaf level {
          ext:help "Recalculate only this IS-IS level";
          type enumeration {
            enum level-1;
            enum level-2;
          }
        }
      }
      // `clear isis neighbor [<system-id>]`. The bare (presence)
      // form tears down every IS-IS adjacency on the instance;
      // with a value it tears down only the neighbor whose System
      // ID (the "System Id" column in `show isis neighbor`)
      // matches. The teardown reuses the hold-timer-expiry path —
      // the adjacency is dropped, Hello+LSP re-originated, the DIS
      // re-elected on LAN, labels/SIDs released and SPF
      // rescheduled — so a live peer's Hellos re-form it from
      // scratch (Down -> Up). Mirrors the OSPF `clear ospf
      // neighbor` shape: a presence list so the bare node is a
      // valid terminal (-> reset all) yet still takes a positional
      // key (-> reset one). The System ID is `xxxx.xxxx.xxxx`, so
      // the arg type is a plain string.
      list neighbor {
        ext:help "Reset IS-IS adjacencies (bare resets all)";
        ext:presence "Reset every IS-IS adjacency";
        key id;
        leaf id {
          ext:help "Reset only the neighbor with this System ID";
          ext:dynamic "isis:neighbor";
          type string;
        }
      }
      container checkpoint {
        ext:help "IS-IS graceful-restart checkpoint storage";
        // Debug entry for the graceful-restart checkpoint storage
        // layer (Phase 5b of docs/design/isis-graceful-restart-
        // restarter.md). Becomes operator-facing once the
        // restart-commit flow lands in Phase 5d.
        leaf write {
          ext:help "Write the current IS-IS state to /var/lib/zebra-rs/checkpoint/isis.cbor";
          type empty;
        }
        leaf clear {
          ext:help "Delete the on-disk IS-IS graceful-restart checkpoint";
          type empty;
        }
      }
      container graceful-restart {
        ext:help "Stage or commit an IS-IS graceful restart";
        // RFC 5306 restarter-side staging + commit. `begin` floods
        // IIH+RR and freezes self-LSP refresh without exiting;
        // `abort` walks the staging back. `commit` extends `begin`
        // with a checkpoint write, a drain window, and process
        // exit so the supervisor (systemd / operator) restarts us
        // -- kernel routes tagged RibType::Isis survive because
        // no ProtoCleanup is dispatched.
        leaf begin {
          ext:help "Stage a graceful restart: flood IIH+RR and freeze self-LSP refresh";
          type empty;
        }
        leaf commit {
          ext:help "Write the GR checkpoint, drain, and exit the process for supervisor-driven restart";
          type empty;
        }
        leaf abort {
          ext:help "Abort a staged graceful restart and resume normal operation";
          type empty;
        }
      }
    }
    container ospf {
      ext:help "OSPFv2 clear actions";
      // Force-recalculate the OSPFv2 SPF for every attached area
      // instead of waiting for the next LSDB event or the 1-second
      // coalescing timer. Mirrors FRR's `clear ip ospf process`
      // SPF-side effect.
      leaf spf {
        ext:help "Force an OSPFv2 SPF recalculation";
        type empty;
      }
      // Juniper-style `clear ospf neighbor [<router-id>]`. The bare
      // (presence) form resets every OSPFv2 adjacency on the
      // instance; with a value it resets only the neighbor whose OSPF
      // Router-ID (the "Neighbor ID" column in `show ospf
      // neighbor`) matches. The Router-ID is a dotted-quad, so the
      // arg type is `inet:ipv4-address`; the runtime matches it
      // against `Neighbor.ident.router_id`, not the interface address.
      //
      // Modeled as a presence list so the node is a valid terminal
      // on its own (-> reset all) yet still accepts a positional key
      // (-> reset one), the same shape as `show bgp neighbor
      // [<addr>]`. No `all` keyword is needed (unlike
      // zebra-bgp-clear.yang) because the bare presence already
      // carries the "every neighbor" meaning.
      list neighbor {
        ext:help "Reset OSPF adjacencies (bare resets all)";
        ext:presence "Reset every OSPF adjacency";
        key id;
        leaf id {
          ext:help "Reset only the neighbor with this OSPF Router-ID";
          ext:dynamic "ospf:neighbor";
          type inet:ipv4-address;
        }
      }
      container checkpoint {
        ext:help "OSPFv2 graceful-restart checkpoint storage";
        // Debug entry for the graceful-restart checkpoint storage
        // layer (Phase 5b). Becomes operator-facing once the
        // restart-commit flow lands in Phase 5d.
        leaf write {
          ext:help "Write the current instance state to /var/lib/zebra-rs/checkpoint/ospf.cbor";
          type empty;
        }
        leaf clear {
          ext:help "Delete the on-disk OSPF graceful-restart checkpoint";
          type empty;
        }
      }
      container graceful-restart {
        ext:help "Stage or commit an OSPFv2 graceful restart";
        // Stage / commit / unstage a planned restart.
        // `begin` (Phase 5c) floods Grace LSAs and sets
        // `gr_capable`; `commit` (Phase 5d) writes the
        // checkpoint and exits the process for the
        // supervisor to restart; `abort` walks the staging
        // back without exiting.
        leaf begin {
          ext:help "Stage a graceful restart: flood Grace LSAs and set gr_capable";
          type empty;
        }
        leaf commit {
          ext:help "Write the GR checkpoint, drain, and exit the process";
          type empty;
        }
        leaf abort {
          ext:help "Abort a staged graceful restart and resume normal operation";
          type empty;
        }
      }
    }
    container ospfv3 {
      ext:help "OSPFv3 clear actions";
      container checkpoint {
        ext:help "OSPFv3 graceful-restart checkpoint storage";
        leaf write {
          ext:help "Write the current instance state to /var/lib/zebra-rs/checkpoint/ospfv3.cbor";
          type empty;
        }
        leaf clear {
          ext:help "Delete the on-disk OSPFv3 graceful-restart checkpoint";
          type empty;
        }
      }
      container graceful-restart {
        ext:help "Stage or commit an OSPFv3 graceful restart";
        leaf begin {
          ext:help "Stage a graceful restart: flood v3 Grace LSAs";
          type empty;
        }
        leaf commit {
          ext:help "Write the GR checkpoint, drain, and exit the process";
          type empty;
        }
        leaf abort {
          ext:help "Abort a staged graceful restart and resume normal operation";
          type empty;
        }
      }
      // Force-recalculate the OSPFv3 SPF for every attached area.
      // Sibling of `clear ospf spf` for the v3 instance.
      leaf spf {
        ext:help "Force an OSPFv3 SPF recalculation";
        type empty;
      }
      // `clear ospfv3 neighbor [<router-id>]` — v3 sibling of the
      // `clear ospf neighbor` surface. Bare (presence) resets every
      // OSPFv3 adjacency; with a value it resets only the neighbor
      // whose OSPF Router-ID (the "Neighbor ID" in `show ospfv3
      // neighbor`) matches. The Router-ID is a dotted-quad, so the
      // arg stays `inet:ipv4-address`; for v3 it is also the
      // `OspfLink.nbrs` map key (RFC 5340 §10). Same presence-list
      // shape as the v2 sibling — see the `container ospf` comment.
      list neighbor {
        ext:help "Reset OSPFv3 adjacencies (bare resets all)";
        ext:presence "Reset every OSPFv3 adjacency";
        key id;
        leaf id {
          ext:help "Reset only the neighbor with this OSPF Router-ID";
          ext:dynamic "ospfv3:neighbor";
          type inet:ipv4-address;
        }
      }
    }
  }
}

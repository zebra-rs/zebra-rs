module zebra-bgp-clear {
  yang-version "1";

  namespace "urn:ietf:params:xml:ns:yang:zebra-bgp-clear";
  prefix "zbc";

  import ietf-inet-types {
    prefix inet;
  }

  import ietf-yang-types {
    prefix yang;
  }

  import configure {
    prefix configure;
  }

  import extension {
    prefix ext;
  }

  organization
    "zebra-rs";

  contact
    "https://github.com/zebra-rs";

  description
    "FRR / IOS-XR style operational `clear bgp <afi> <peer> [soft [in|out]]`
     command surface.

     Path layout (per AFI container — ipv4 / ipv6 / vpnv4 / evpn):

       /clear/bgp/<afi>/neighbor                  hard reset
       /clear/bgp/<afi>/neighbor/soft             soft, both directions
       /clear/bgp/<afi>/neighbor/soft/in          soft, inbound only
       /clear/bgp/<afi>/neighbor/soft/out         soft, outbound only

     plus an AFI-less form directly under /clear/bgp — same subtree,
     no AFI/SAFI filter (`clear bgp <peer-or-all> [soft [in|out]]`):

       /clear/bgp/neighbor[/soft[/in|/out]]

     The list key on `neighbor` is a `peer-id-or-all` — the peer's IP
     literal, an `interface-neighbor` name (IPv6 unnumbered), or the
     keyword `all` to target every peer at that AFI (every peer
     outright in the AFI-less form).";

  /* =========================================================
   * Types
   * ========================================================= */

  typedef peer-id-or-all {
    description
      "BGP peer address (IPv4 or IPv6), an `interface-neighbor` name
       (IPv6 unnumbered peers are keyed by interface — the name is
       their only typeable identity), or the literal `all` meaning
       every peer at the enclosing AFI/SAFI. The same typedef is used
       across all four AFI containers — under vpnv4 the runtime only
       resolves IPv4 transports (and reports `peer not found` for IPv6
       inputs); evpn accepts either v4 or v6 transports natively.";
    type union {
      type inet:ipv4-address;
      type inet:ipv6-address;
      // `all` is an enumeration, NOT `type string { pattern "all" }`:
      // a pattern arm full-matches the entire remaining line (the
      // description-LINE semantics), so it can never match when more
      // tokens follow — `clear bgp ipv4 all soft out` was Nomatch in
      // every spelling. Enum arms match per-token (and abbreviate),
      // exactly like the `summary` key arm in exec.yang.
      type enumeration {
        enum all;
      }
      // Interface-neighbor names. Pattern-less so it word-matches a
      // single token (`clear bgp ipv4 neighbor i1 soft out` keeps
      // walking into `soft`); addresses and the full `all` keyword
      // still win over it via Exact-over-Partial. Listed last so the
      // typed arms get first shot.
      type string;
    }
  }

  /* =========================================================
   * Reusable action subtree
   * ========================================================= */

  grouping bgp-clear-neighbor-actions {
    description
      "The `neighbor <key> [soft [in|out]]` subtree that hangs off
       every AFI container under /clear/bgp/. Used by ipv4, ipv6,
       vpnv4, evpn alike.";
    list neighbor {
      ext:help "Clear one or all BGP neighbors";
      ext:presence "BGP neighbor clear actions";
      key address;
      leaf address {
        ext:help "Neighbor address (or all)";
        ext:dynamic "bgp:neighbor";
        type peer-id-or-all;
      }
      container soft {
        presence
          "Soft-clear (both directions when bare; narrow with `in` or `out`)";
        ext:help "Re-apply policy without bouncing the session";
        leaf in {
          type empty;
          ext:help "Inbound only";
        }
        leaf out {
          type empty;
          ext:help "Outbound only";
        }
        must "not(in and out)" {
          error-message "soft in and soft out are mutually exclusive";
        }
      }
    }
  }

  /* =========================================================
   * Augment into the zebra-rs configure tree
   * ========================================================= */

  augment "/configure:clear" {
    description
      "Add the `bgp <afi> ...` clear surface to /configure:clear.
       Each AFI container reuses the same neighbor/soft grouping.";
    container bgp {
      ext:help "BGP clear actions";
      // AFI-less form: `clear bgp {<peer>|all} [soft [in|out]]` clears
      // across every AFI/SAFI. The positional routing is safe next to
      // the AFI keyword children because the matcher only takes the
      // default-child descent on a *strictly better* match: `ipv4`
      // etc. keyword-match Exact (or Partial when abbreviated) while
      // the key's pattern-less string arm is only ever Partial — so
      // any AFI spelling, including abbreviations, still wins and an
      // IP literal / interface name / `all` falls through to the key.
      ext:default-child "neighbor";
      uses bgp-clear-neighbor-actions;
      // FRR-style positional form: a peer address (or `all`) typed
      // straight after the AFI (`clear bgp ipv4 10.0.0.1 [soft ...]`)
      // is routed into the `neighbor` list by the matcher via
      // `ext:default-child` — resolving to the same path and args as
      // the explicit `clear bgp <afi> neighbor <peer>` spelling.
      container ipv4 {
        ext:help "IPv4 unicast";
        ext:default-child "neighbor";
        uses bgp-clear-neighbor-actions;
      }
      container ipv6 {
        ext:help "IPv6 unicast";
        ext:default-child "neighbor";
        uses bgp-clear-neighbor-actions;
      }
      container vpnv4 {
        ext:help "VPNv4 (BGP/MPLS-VPN, RFC 4364)";
        ext:default-child "neighbor";
        uses bgp-clear-neighbor-actions;
      }
      container evpn {
        ext:help "L2VPN EVPN (RFC 7432)";
        ext:default-child "neighbor";
        uses bgp-clear-neighbor-actions;
        // `clear bgp evpn dup-addr vni <all|N> [mac M | ip I]` (FRR's
        // `clear evpn dup-addr`): release detected duplicate addresses —
        // every one in the VNI, or the one MAC or IP named — and re-run
        // their routes.
        container dup-addr {
          ext:help "Release EVPN duplicate addresses";
          list vni {
            ext:help "VNI (or all)";
            ext:presence "Release every duplicate address in the VNI";
            key id;
            leaf id {
              ext:help "VNI, or all";
              type union {
                type enumeration {
                  enum all;
                }
                type uint32 {
                  range "1..16777215";
                }
              }
            }
            leaf mac {
              ext:help "Release this MAC";
              type yang:mac-address;
            }
            leaf ip {
              ext:help "Release this IP";
              type inet:ip-address;
            }
          }
        }
      }
      // Debug / test-injection surface for the RFC 9251 EVPN Type-7
      // (IGMP/MLD Join Synch) and Type-8 (Leave Synch) routes. Each action
      // takes one comma-separated spec token `vni,esi,group[,source]`:
      //   - vni    L2VPN VNI (selects RD <router-id>:VNI and the EVI RT)
      //   - esi    10-octet ESI, colon-hex (00:01:..:09) or 20 hex digits
      //   - group  multicast group address
      //   - source multicast source for (S,G); omit for (*,G)
      // It drives `evpn_originate_igmp_*_sync` directly so a route reflector
      // can be exercised end-to-end (BDD) without the ES/DF dataplane, which
      // is still deferred. Flags are derived from the group family
      // (IGMPv3 / MLDv2) and the Type-8 Maximum Response Time defaults.
      container debug {
        ext:help "BGP debug / test-injection actions";
        list igmp-join-sync-originate {
          ext:presence "Originate an EVPN Type-7 IGMP/MLD Join Synch route";
          ext:help "Originate a Type-7 Join Synch route (RFC 9251, debug)";
          key spec;
          leaf spec {
            ext:help "vni,esi,group[,source]";
            type string;
          }
        }
        list igmp-join-sync-withdraw {
          ext:presence "Withdraw an EVPN Type-7 IGMP/MLD Join Synch route";
          ext:help "Withdraw a Type-7 Join Synch route (RFC 9251, debug)";
          key spec;
          leaf spec {
            ext:help "vni,esi,group[,source]";
            type string;
          }
        }
        list igmp-leave-sync-originate {
          ext:presence "Originate an EVPN Type-8 IGMP/MLD Leave Synch route";
          ext:help "Originate a Type-8 Leave Synch route (RFC 9251, debug)";
          key spec;
          leaf spec {
            ext:help "vni,esi,group[,source]";
            type string;
          }
        }
        list igmp-leave-sync-withdraw {
          ext:presence "Withdraw an EVPN Type-8 IGMP/MLD Leave Synch route";
          ext:help "Withdraw a Type-8 Leave Synch route (RFC 9251, debug)";
          key spec;
          leaf spec {
            ext:help "vni,esi,group[,source]";
            type string;
          }
        }
      }
    }
  }
}

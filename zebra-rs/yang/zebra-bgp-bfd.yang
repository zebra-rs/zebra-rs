module zebra-bgp-bfd {
  yang-version "1";

  namespace "urn:ietf:params:xml:ns:yang:zebra-bgp-bfd";
  prefix "zbb";

  import ietf-bgp {
    prefix bgp;
  }

  import config {
    prefix config;
  }

  import configure {
    prefix configure;
  }

  import extension {
    prefix ext;
  }

  organization
    "zebra-rs";

  contact
    "https://github.com/zebra-rs";

  description
    "FRR-style BFD attachment for BGP. A flat `bfd` container appears
     both at the BGP instance level (a default applied to every neighbor)
     and under each neighbor (an override):

       router bgp {
         bfd {
           enabled true;          // blanket-enable all neighbors
           echo-mode receive;    // default Echo role
         }
         neighbor 10.0.0.5 {
           remote-as 65501;
           bfd {
             enabled true;
             multihop true;       // eBGP-over-loopback; iBGP infers this
             minimum-ttl 250;
             echo-mode both;      // override (single-hop neighbors only)
           }
         }
       }

     The effective value of each `bfd` leaf is the per-neighbor setting if
     present, else the instance default, else a hard default. `enabled true`
     at the instance level activates BFD on every neighbor (a per-neighbor
     `enabled false` opts one out). Echo is **single-hop only** (RFC 5883
     multihop has no Echo), so `echo-mode` is inert on multihop sessions
     (iBGP and multihop eBGP). Hop-mode (`multihop`) and `minimum-ttl` are
     per-neighbor only.";

  revision 2026-06-12 {
    description
      "Add `detect-offload`: offload control-packet expiration detection
       (the RFC 5880 §6.8.4 detection timer) to the per-interface
       XDP/eBPF helper once the session is Up. Single-hop only. Also
       correct the stale `echo-mode` description: Echo supports IPv6
       single-hop sessions, not only IPv4.";
    reference
      "RFC 5880 §6.8.4 (Calculating the Detection Time); RFC 5881 §5
       (GTSM).";
  }

  revision 2026-06-01 {
    description
      "Add instance-level `router bgp { bfd {} }` defaults with
       per-neighbor override, and single-hop `echo-mode`
       (transmit/receive/both) + echo-transmit/receive-interval.";
    reference
      "RFC 5880 §6.4 (Echo). FRR bfdd echo-mode; single-hop eBGP only.";
  }

  revision 2026-05-31 {
    description
      "Add `multihop` hop-mode override and multihop `minimum-ttl`.";
    reference
      "RFC 5883 (Multihop BFD). FRR `bfd` peer `multihop` / `minimum-ttl`.";
  }

  revision 2026-05-19 {
    description "Initial revision (PR 5b — storage only).";
    reference
      "FRR `neighbor X bfd` / `neighbor X bfd profile P`. RFC 5880, RFC 9314.";
  }

  // Leaves shared by the instance-level and per-neighbor `bfd {}` containers.
  // No YANG `default` (absent ⇒ inherit, then a hard default in code).
  grouping bgp-bfd-common {
    leaf enabled {
      ext:help "Activate BFD (omit to inherit the instance default)";
      type boolean;
      description
        "Activate BFD. At the instance level, `true` blanket-enables BFD
         on every neighbor; per neighbor it overrides that default, so
         `false` opts a single neighbor out. Absent at both levels ⇒ off.";
    }
    leaf echo-mode {
      ext:help "BFD Echo role (transmit | receive | both)";
      type enumeration {
        enum transmit { description "Originate Echo only."; }
        enum receive { description "Advertise + reflect only."; }
        enum both { description "Both."; }
      }
      description
        "Enable the BFD Echo function (RFC 5880 §6.4). **Single-hop only**
         — RFC 5883 multihop has no Echo, so this is inert on multihop
         sessions (iBGP / multihop eBGP). Both IPv4 and IPv6 single-hop
         sessions are supported. Overrides the instance default; absent ⇒
         inherit (Echo off if unset).";
    }
    leaf echo-transmit-interval {
      ext:help "Echo transmit interval (ms)";
      type uint32;
      units "milliseconds";
      description
        "Rate we originate Echo at (echo-mode `transmit`/`both`). Hard
         default 50 ms when unset at every level.";
    }
    leaf echo-receive-interval {
      ext:help "Advertised Required Min Echo RX Interval (ms)";
      type uint32;
      units "milliseconds";
      description
        "Advertised Required Min Echo RX (echo-mode `receive`/`both`).
         Hard default 50 ms when unset.";
    }
    leaf detect-offload {
      ext:help "Offload expiration detection to the XDP data plane (kernel)";
      type boolean;
      description
        "Once the session is Up, detect missing BFD control packets in
         the kernel: the XDP/eBPF data plane re-arms a
         per-session timer on every arriving control packet (UDP/3784,
         TTL 255) and drives the session Down with Control Detection
         Time Expired when they stop (RFC 5880 §6.8.4) — immune to
         daemon scheduling latency. The userspace detection timer stays
         armed as a stretched backstop. **Single-hop only** — inert on
         multihop sessions (the XDP program runs on attached ports). Absent ⇒
         inherit (false: detection in userspace).";
    }
  }

  grouping bgp-neighbor-bfd-extension {
    description
      "FRR-style flat `bfd { ... }` block on a BGP neighbor — overrides the
       instance-level `bfd {}` defaults, per leaf.";

    container bfd {
      ext:help "BFD attachment for this neighbor";
      description
        "Per-neighbor BFD. Each leaf overrides the BGP instance's `bfd {}`
         default; an unset leaf inherits it.";
      uses bgp-bfd-common;

      leaf multihop {
        ext:help "Force BFD hop mode for this neighbor";
        type boolean;
        description
          "Explicit hop-mode override (per-neighbor only). When unset, the
           session is multihop iff the BGP session is iBGP, mirroring FRR's
           `PEER_IS_MULTIHOP`. Set `true` for eBGP-over-loopback or `false`
           to force single-hop. Multihop uses UDP/4784 and a relaxed TTL
           floor; single-hop uses UDP/3784 with GTSM (TTL=255).";
      }

      leaf minimum-ttl {
        ext:help "Multihop: lowest accepted received TTL";
        type uint8 {
          range "1..254";
        }
        default 254;
        description
          "Multihop only (per-neighbor): minimum TTL accepted on incoming
           control packets (RFC 5883). Ignored on single-hop sessions.";
      }
    }
  }

  grouping bgp-router-bfd-extension {
    description
      "Instance-level BFD defaults for a BGP instance, inherited by every
       neighbor and overridable per neighbor.";

    container bfd {
      ext:help "BFD defaults for this BGP instance";
      description
        "Defaults applied to every neighbor's BFD session. `enabled true`
         here blanket-enables BFD on all neighbors; a per-neighbor
         `bfd { enabled false }` opts one out. Every leaf is overridable per
         neighbor. (Hop-mode / minimum-ttl are per-neighbor only.)";
      uses bgp-bfd-common;
    }
  }

  /* =========================================================
   * Augments into the zebra-rs configure tree
   * ========================================================= */

  augment "/configure:set/config:router/bgp:bgp" {
    description "Instance-level BFD defaults for BGP (set).";
    uses bgp-router-bfd-extension;
  }

  augment "/configure:delete/config:router/bgp:bgp" {
    description "Instance-level BFD defaults for BGP (delete).";
    uses bgp-router-bfd-extension;
  }

  augment "/configure:set/config:router"
        + "/bgp:bgp/bgp:neighbor" {
    description
      "Attach the flat bfd block to BGP neighbors in the
       candidate-set subtree.";
    uses bgp-neighbor-bfd-extension;
  }

  augment "/configure:delete/config:router"
        + "/bgp:bgp/bgp:neighbor" {
    description
      "Same attachment for the delete subtree so
       `delete router bgp neighbor X bfd ...` is path-valid.";
    uses bgp-neighbor-bfd-extension;
  }
}

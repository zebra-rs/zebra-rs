module zebra-features {
  yang-version "1";

  namespace "urn:ietf:params:xml:ns:yang:zebra-features";
  prefix "feat";

  description
    "Central registry of zebra-rs optional-feature switches (RFC 7950
     feature statements). A module that wants conditional schema
     imports this registry (conventionally with prefix `feat`) and
     guards nodes with `if-feature feat:NAME`; the guarded nodes exist
     only while the daemon is started with `--feature NAME` (a bare
     name on the flag resolves to this module — `--feature insomnia`
     means `zebra-features:insomnia`). Features default to off, so
     guarded nodes are absent from the schema tree unless explicitly
     enabled.

     Module-local features are also possible (`--feature MODULE:NAME`),
     but prefer registering here so operators have one place to look.";

  feature insomnia {
    description
      "Optional system-service configuration that zebra-rs stores but
       does not enforce itself. It gates:
         - `firewall` and `show firewall`;
         - `vpn` (IPsec) and `show vpn`;
         - `vrrp` and `show vrrp`;
         - `service` (the DHCP server and relay trees) and `show dhcp
           server|relay` / `show dhcpv6`;
       all enforced by the out-of-process insomnia daemon. (The DHCP
       client, `interface <name> ipv4 address dhcp`, is zebra-rs's own
       and not gated.)

       It also changes what one ungated leaf does. With the feature
       zebra-rs is the configuration owner of the whole system, so
       `system hostname` is applied to the system by zebra-rs itself:
       the kernel host name and /etc/hostname, when zebra-rs runs in the
       default network namespace. Without the feature that leaf names
       the router inside zebra-rs only.

       Formerly named `iso`. `--feature iso` still enables it, with a
       deprecation warning at startup; use `--feature insomnia`.";
  }

  feature etree {
    description
      "No longer gates anything; kept so `--feature etree` is still
       accepted without a warning.

       EVPN E-Tree (RFC 8317) — root and leaf attachment circuits under
       `router bgp afi-safi evpn etree`, and `show bgp evpn etree` — is
       always available. It was gated until a leaf's broadcast,
       multicast and unknown unicast were kept from leaves on other PEs
       over every encapsulation: MPLS by the leaf label, VXLAN by the
       leaf-only IMET colour, and SRv6 by the leaf argument. Over VXLAN
       two PEs that both have leaf and root ACs still exchange their
       leaves' BUM, and `show bgp evpn etree` warns about such a domain.
       A leaf AC needs the cradle data plane; a commit naming one
       without it is refused.";
  }
}

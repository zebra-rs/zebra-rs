module zebra-bgp-interface-neighbor {
  yang-version "1";

  namespace "urn:ietf:params:xml:ns:yang:zebra-bgp-interface-neighbor";
  prefix "zbin";

  import ietf-inet-types {
    prefix inet;
  }

  import config {
    prefix config;
  }

  import ietf-bgp {
    prefix bgp;
  }

  import configure {
    prefix configure;
  }

  import extension {
    prefix ext;
  }

  organization
    "zebra-rs";

  contact
    "https://github.com/zebra-rs";

  description
    "BGP interface-keyed neighbor (IPv6 unnumbered). Modelled on the
     FRR `neighbor IFNAME interface remote-as …` workflow but
     surfaced as a separate top-level `interface-neighbor` list under
     `router bgp` — cleaner schema than a polymorphic `neighbor` keyed
     by either IP or interface, and matches the IOS-XR shape.

     Resulting config:

       interface eth0 {
         ipv6 {
           router-advertisements { send-advertisements true; }
         }
       }
       router bgp {
         interface-neighbor eth0 {
           remote-as 65002;
         }
       }

     Operation:
       1. The ND subsystem (started by the first `router bgp` or
          `ipv6 router-advertisements` line) ingests inbound RAs and
          emits NeighborDiscovered { ifindex, src=link-local } events.
       2. Once the interface exists, BGP materializes a dormant Peer
          keyed by PeerKey::Interface(ifindex), listed as Idle in
          `show bgp summary`. The first RA from the neighbor fills in
          its link-local as `address` and starts the session.
       3. The session establishes over fe80::%ifindex. RFC 8950
          Extended Next Hop Encoding is advertised automatically, so
          IPv4 routes travel with an IPv6 link-local next-hop and are
          installed via that link-local on the interface.";

  typedef remote-as-type {
    type union {
      type inet:as-number;
      type enumeration {
        enum external {
          description
            "FRR-style shorthand — the remote AS is anything other
             than the local one. The neighbor's AS is learned from its
             OPEN on each session; an OPEN from the local AS is refused
             with Bad Peer AS.";
        }
        enum internal {
          description
            "FRR-style shorthand — the remote AS equals the local
             ASN. iBGP session.";
        }
      }
    }
    description
      "Remote AS specification. Accepts either a numeric AS (matching
       the regular `neighbor X remote-as N` form) or the FRR shorthand
       `external` / `internal`. Unnumbered configs are noisier without
       the shorthand.";
  }

  grouping bgp-interface-neighbor-extension {
    description
      "Container hung off `router bgp`.";
    list interface-neighbor {
      // A bare `interface-neighbor <ifname>` can never materialize a peer —
      // without a `remote-as` (or a `neighbor-group` that supplies one) the
      // ND-triggered materialization silently no-ops, so it's dead config.
      // Reject the key-only entry at commit, and prune it when its last
      // child is deleted, so a meaningless entry can't linger.
      ext:non-empty "remote-as or neighbor-group";
      key "interface";
      ext:help "BGP interface-keyed neighbor (IPv6 unnumbered)";
      description
        "One entry per outbound interface participating in unnumbered
         BGP. Peer state is materialized only when the ND subsystem
         observes a Router Advertisement on the interface (so the
         operator must also enable
         `interface X ipv6 router-advertisements send-advertisements
         true`).";
      leaf interface {
        ext:help "Interface for the unnumbered BGP peer";
        type string;
        description
          "Outbound interface name. Resolved to ifindex via the RIB
           link table; the per-leaf callback silently defers
           materialization until the kernel surfaces the link.";
      }
      leaf neighbor-group {
        ext:help "Neighbor-group to inherit attributes from";
        type string;
        description
          "Optional reference to a `neighbor-group` whose attributes
           the materialized peer inherits. Plain string (not a
           leafref) so the interface-neighbor can be staged before
           the group definition lands — same convention as other
           zebra-bgp-* augments.";
      }
      leaf remote-as {
        ext:help "Remote autonomous system number";
        type remote-as-type;
        description
          "Remote AS. May be omitted if the referenced
           `neighbor-group` carries one; otherwise mandatory at
           session-establishment time (an unset value silently
           prevents materialization).";
      }
      container timers {
        ext:help "Per-neighbor BGP timers";
        description
          "Session timers for this unnumbered peer. The addressed
           `neighbor <addr> timers` leaves cannot reach one: their
           callbacks resolve the peer by remote address, and an
           interface-neighbor peer is keyed by ifindex
           (`PeerKey::Interface`), so it is not in that lookup.

           Deliberately NOT `uses neighbor-group-timers` (the grouping
           the addressed neighbor takes), for the same reason the
           per-VRF neighbor hand-mirrors it: two of that grouping's
           leaves (originate-interval, delay-open-time) are staged onto
           `PeerConfig::timer` and never read by any timer-arming path,
           so mirroring it here would expose knobs that silently do
           nothing. Only the leaves `crate::bgp::timer::Config` actually
           consumes are modelled.

           Values are staged on the interface-neighbor config and
           copied onto the peer when it materializes, so they apply to
           a neighbor configured before its interface or its first
           Router Advertisement exists. An edit made while the peer is
           already materialized writes through to it, matching the
           addressed neighbor's callbacks. When the change takes
           effect is per-leaf: `hold-time` is negotiated, so it applies
           to the next session establishment (`clear bgp`); the others
           follow the runtime semantics described on each leaf.";
        leaf advertisement-interval {
          ext:help "MinRouteAdvertisementInterval (MRAI) in seconds";
          type uint16 {
            range "0..max";
          }
          units "seconds";
          description
            "Per-neighbor MRAI: how long the advertise debounce
             coalesces burst route changes before flushing to this
             peer. `0` disables the debounce (flush on the next
             event-loop tick). When unset the peer follows the
             instance-level `router bgp timer adv-interval`, which does
             reach interface-keyed peers (30s eBGP / 5s iBGP by
             default).";
          reference
            "RFC 4271: A Border Gateway Protocol 4 (BGP-4),
             Section 9.2.1.1.";
        }
        leaf connect-retry-time {
          ext:help "ConnectRetry timer (seconds)";
          type uint16 {
            range "1..max";
          }
          units "seconds";
          description
            "Time interval for the ConnectRetryTimer, pacing the
             Connect/Active redial loop. Defaults to 30s when unset.";
          reference
            "RFC 4271: A Border Gateway Protocol 4 (BGP-4),
             Section 8.2.2.";
        }
        leaf hold-time {
          ext:help "Hold timer negotiated with the peer (seconds)";
          type uint16 {
            range "0 | 3..65535";
          }
          units "seconds";
          description
            "Hold Time proposed in this session's OPEN; the session
             uses the smaller of this and the peer's, and the keepalive
             interval is a third of the result. Must be 0 or at least
             3. Defaults to 180s when unset.";
          reference
            "RFC 4271: A Border Gateway Protocol 4 (BGP-4),
             Section 4.2.";
        }
        leaf idle-hold-time {
          ext:help "IdleHold timer before reconnect (seconds)";
          type uint16 {
            range "0..max";
          }
          units "seconds";
          description
            "Time the FSM dwells in Idle before the automatic restart
             re-arms the connect. Defaults to 5s when unset. A change
             on a materialized, dialable peer re-arms the running
             timer, so it takes effect without a session reset.";
        }
      }
    }
  }

  /* =========================================================
   * Augments into the zebra-rs configure tree
   * ========================================================= */

  augment "/configure:set/config:router/bgp:bgp" {
    description
      "Attach the interface-neighbor list in the candidate-set
       subtree.";
    uses bgp-interface-neighbor-extension;
  }

  augment "/configure:delete/config:router/bgp:bgp" {
    description
      "Same attachment for the delete subtree so
       `delete router bgp interface-neighbor X` is path-valid.";
    uses bgp-interface-neighbor-extension;
  }
}

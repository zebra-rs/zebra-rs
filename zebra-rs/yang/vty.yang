module vty {
  yang-version "1";

  namespace "urn:ietf:params:xml:ns:yang:zebra-vty";
  prefix "vty";

  import extension {
    prefix ext;
  }

  organization
    "zebra-rs project";
  contact
    "https://zebra.dev";
  description
    "VTY (CLI) configuration for zebra-rs.";

  revision "2026-05-18" {
    description
      "Initial revision.";
  }

  grouping vty {
    description
      "VTY configuration container.";
  }
}

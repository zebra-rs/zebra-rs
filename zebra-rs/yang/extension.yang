module extension {
  yang-version "1";

  namespace "urn:ietf:params:xml:ns:yang:zebra";
  prefix "coreswitch";

  extension help {
    description "help";
    argument "help";
  }

  extension sort {
    description "sort";
    argument "sort";
  }

  extension no-sort {
    description
      "Keep CLI completion in YANG declaration order for this leaf
       instead of alphabetizing it.";
    argument "no-sort";
  }

  extension presence {
    description "presence";
    argument "presence";
  }

  extension dynamic {
    description "dyanamic completion";
    argument "dynamic";
  }

  extension default-child {
    description
      "Names a child of this container whose key may be supplied
       positionally — without typing the child's own keyword. When no
       sibling keyword matches the input but it type-matches the named
       child's key, the CLI matcher descends into that child as if its
       keyword had been typed (e.g. `show bgp A.B.C.D` is rewritten to
       `show bgp ipv4 A.B.C.D`). The argument is the child node name.";
    argument "default-child";
  }

  extension positional {
    description
      "Marks a list as reachable only through its parent's
       `ext:default-child`: the list's own keyword is neither matched
       against input nor offered in completion, so the key value must be
       typed positionally (e.g. `show ip route A.B.C.D/M` — there is no
       `show ip route prefix …` spelling). The argument documents the
       positional spelling.";
    argument "positional";
  }

  extension non-empty {
    description
      "Forbids key-only entries on this `list`: every entry must carry at
       least one child node, so a bare `... <key>` is rejected at commit.
       (YANG has no clean `must`-style 'at least one child' constraint and
       this config tree does not evaluate `must`.) The argument is the
       human-readable requirement echoed in the error, e.g.
       'network or redistribute'.";
    argument "non-empty";
  }
}

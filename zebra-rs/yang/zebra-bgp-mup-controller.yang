module zebra-bgp-mup-controller {
  yang-version "1";

  namespace "urn:ietf:params:xml:ns:yang:zebra-bgp-mup-controller";
  prefix "zbmupc";

  import ietf-bgp {
    prefix bgp;
  }

  import config {
    prefix config;
  }

  import configure {
    prefix configure;
  }

  import ietf-inet-types {
    prefix inet;
  }

  organization
    "zebra-rs";

  contact
    "https://github.com/zebra-rs";

  description
    "BGP MUP Controller (MUP-C) extensions to the BGP candidate-config
     tree. Adds a `mup-c` container directly under the BGP instance
     (SAFI 85, draft-ietf-bess-mup-safi). When enabled, the BGP task
     spawns an in-process
     MUP controller that terminates PFCP/N4 (3GPP TS 29.244) as a UP-node,
     learns mobile sessions and originates Type-1 / Type-2
     Session-Transformed routes.

     Resulting CLI / config shape:

       router bgp {
         mup-c {
           enabled true;
           controller-address 2001:db8::1;
           upf-address 10.100.0.1;
           pfcp {
             node-id 10.0.0.1;
             listen-address ::;
             port 8805;
           }
           srv6 { locator LOC1; }
         }
       }";

  reference
    "draft-ietf-bess-mup-safi: BGP Extensions for the Mobile User Plane
     (MUP) SAFI
     3GPP TS 29.244: Interface between the Control Plane and the User
     Plane Nodes (PFCP)";

  grouping bgp-mup-c-extension {
    description
      "MUP controller config, hung directly off the BGP instance.";

    container mup-c {
      ext:help "BGP MUP Controller (PFCP/N4 UP-node)";
      description
        "BGP MUP Controller (MUP-C). Terminates PFCP/N4 as a UP-node and
         originates MUP Session-Transformed routes from learned sessions.";

      leaf enabled {
        ext:help "Spawn the in-process MUP controller (PFCP listener)";
        type boolean;
        default false;
        description
          "Master switch. When true, the BGP task spawns the in-process
           MUP controller (PFCP listener); when false it is torn down.";
      }

      leaf controller-address {
        ext:help "Controller IPv6 next hop (ST routes)";
        type inet:ipv6-address;
        description
          "Controller IPv6 address advertised as the next hop on
           originated Type-1 / Type-2 Session-Transformed routes.";
      }

      leaf upf-address {
        ext:help "Core-side UPF endpoint for originated ST2 routes";
        type inet:ip-address;
        description
          "Core (N6) UPF endpoint address used as the Type-2 Session
           Transformed (ST2) route endpoint when the PFCP session carries
           no core-side GTP tunnel (the common N6-breakout case, where the
           SMF programs only the access/gNB tunnel). A session that does
           learn a core-facing F-TEID over PFCP (e.g. an N9 tunnel) keeps
           that learned endpoint in preference to this configured one.
           Pair with `upf-teid`: an ST2 needs both a core endpoint and a
           (non-zero) core TEID to be originated.";
      }

      leaf upf-teid {
        ext:help "Core-side GTP-U TEID for originated ST2 routes";
        type uint32;
        description
          "Core (N6) GTP-U TEID paired with `upf-address`. Used as the ST2
           route TEID when the PFCP session carries no core-side F-TEID. An
           ST2 is a core/uplink route, so it never borrows the access (gNB)
           tunnel's TEID; without a learned or configured core TEID no ST2 is
           originated. A learned core F-TEID takes precedence. A TEID of 0 is
           invalid (draft §3.1.4.1) and yields no ST2.";
      }

      container pfcp {
        ext:help "PFCP/N4 listener parameters (3GPP TS 29.244)";
        description
          "PFCP / N4 listener parameters (3GPP TS 29.244).";

        leaf node-id {
          ext:help "Our PFCP Node ID returned in responses";
          type inet:ip-address;
          description
            "Our PFCP Node ID, returned in responses. Falls back to the
             bind address / controller-address when unset.";
        }
        leaf listen-address {
          ext:help "PFCP listen address (default all addresses)";
          type inet:ip-address;
          description
            "PFCP listen address. Defaults to `::` (all addresses) when
             unset.";
        }
        leaf port {
          ext:help "PFCP listen port (default 8805)";
          type inet:port-number;
          description
            "PFCP listen port. Defaults to 8805 when unset.";
        }
      }

      container srv6 {
        ext:help "SRv6 parameters for originated routes";
        description
          "SRv6 parameters for originated routes (route phase).";
        leaf locator {
          ext:help "SRv6 locator name for per-session SIDs";
          type string;
          description
            "Name of the SRv6 locator per-session SIDs are drawn from.";
        }
      }

      leaf architecture {
        ext:help "Mobile architecture served (informational)";
        type enumeration {
          enum "3gpp-5g";
        }
        default "3gpp-5g";
        description
          "Mobile architecture the controller serves. Informational.";
      }
    }
  }

  augment "/configure:set/config:router/bgp:bgp" {
    description "MUP controller config under the BGP instance (set).";
    uses bgp-mup-c-extension;
  }

  augment "/configure:delete/config:router/bgp:bgp" {
    description "MUP controller config under the BGP instance (delete).";
    uses bgp-mup-c-extension;
  }
}

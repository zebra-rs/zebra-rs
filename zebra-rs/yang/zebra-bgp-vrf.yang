module zebra-bgp-vrf {
  yang-version "1";

  namespace "urn:ietf:params:xml:ns:yang:zebra-bgp-vrf";
  prefix "zbv";

  import ietf-inet-types {
    prefix inet;
  }

  import ietf-yang-types {
    prefix yang;
  }

  import ietf-bgp {
    prefix bgp;
  }

  import zebra-afi-safi {
    prefix zas;
  }

  import zebra-bgp-afi-knobs {
    prefix zbak;
  }

  import config {
    prefix config;
  }

  import configure {
    prefix configure;
  }

  import extension {
    prefix ext;
  }

  organization
    "zebra-rs";

  contact
    "https://github.com/zebra-rs";

  description
    "Per-VRF BGP configuration for zebra-rs, modelled after Cisco
     IOS-XR. The Route Distinguisher lives in the BGP context
     (`router bgp { vrf X { rd ...; } }`) — keeping it close to the
     protocol that actually emits VPNv4 / VPNv6 NLRIs — while RT
     import/export policy continues to live on the top-level
     /vrf/<name>/{ipv4,ipv6}/route-target leaves added previously.

     Resulting CLI / config shape:

       router bgp {
         vrf vrf1 {
           rd 65000:10;
           router-id 10.0.0.1;
           label-mode per-vrf;
           neighbor 192.0.2.1 {
             remote-as 65001;
             description \"CE1\";
           }
           afi-safi {
             ipv4 {
               network 10.10.0.0/16;
             }
             ipv6 { /* same shape */ }
           }
         }
       }

     `vrf` is keyed by a plain string (not a leafref to /vrf), so a
     `router bgp vrf X` block can be parsed before `vrf X` is
     declared at the top level — same staging-friendly pattern used
     by IS-IS for `block` and `locator` references.

     This schema lands in step 11 of the BGP MPLS/VPN refactor;
     the config callbacks that consume it arrive with `BgpVrfConfig`
     in step 12, and the per-VRF task spawn lands in step 13. Until
     then the leaves are parse-only — committing a `router bgp vrf X`
     block records the intent but doesn't yet alter daemon
     behaviour.";

  reference "RFC 4364: BGP/MPLS IP VPNs §4.2 (Route Distinguishers)";

  typedef route-distinguisher {
    type string {
      pattern
          '(6553[0-5]|655[0-2][0-9]|65[0-4][0-9]{2}|'
        + '6[0-4][0-9]{3}|[1-5][0-9]{4}|[1-9][0-9]{0,3}|0)'
        + ':'
        + '(429496729[0-5]|42949672[0-8][0-9]|'
        + '4294967[01][0-9]{2}|429496[0-6][0-9]{3}|'
        + '42949[0-5][0-9]{4}|4294[0-8][0-9]{5}|'
        + '429[0-3][0-9]{6}|42[0-8][0-9]{7}|'
        + '4[01][0-9]{8}|[1-3][0-9]{9}|'
        + '[1-9][0-9]{0,8}|0)'
        + '|'
        + '((25[0-5]|2[0-4][0-9]|1[0-9]{2}|[1-9]?[0-9])\.){3}'
        + '(25[0-5]|2[0-4][0-9]|1[0-9]{2}|[1-9]?[0-9])'
        + ':'
        + '(6553[0-5]|655[0-2][0-9]|65[0-4][0-9]{2}|'
        + '6[0-4][0-9]{3}|[1-5][0-9]{4}|[1-9][0-9]{0,3}|0)'
        + '|'
        + '(429496729[0-5]|42949672[0-8][0-9]|'
        + '4294967[01][0-9]{2}|429496[0-6][0-9]{3}|'
        + '42949[0-5][0-9]{4}|4294[0-8][0-9]{5}|'
        + '429[0-3][0-9]{6}|42[0-8][0-9]{7}|'
        + '4[01][0-9]{8}|[1-3][0-9]{9}|'
        + '[1-9][0-9]{0,8}|0)'
        + ':'
        + '(6553[0-5]|655[0-2][0-9]|65[0-4][0-9]{2}|'
        + '6[0-4][0-9]{3}|[1-5][0-9]{4}|[1-9][0-9]{0,3}|0)';
    }
    description
      "BGP/MPLS VPN Route Distinguisher in operator-friendly notation
       (no leading type-number prefix). Three encodings are accepted:

         Type 0:  2-byte-ASN:4-byte-number    e.g. 65000:10
         Type 1:  IPv4-address:2-byte-number  e.g. 192.0.2.1:10
         Type 2:  4-byte-ASN:2-byte-number    e.g. 4200000000:10

       Disambiguation between Type 0 and Type 2 is by the magnitude
       of the first field: <= 65535 means Type 0, otherwise Type 2.
       Type 1 is recognised by the dotted-quad in the first field.

       The RD is prepended to each VPN route originating from the
       VRF to make it unique in the global VPNv4 / VPNv6 RIB.

       Wire format and pattern are identical to a Route Target —
       the two are kept as separate typedefs purely for documentation
       clarity (RD = uniqueness, RT = import/export filtering).";
    reference
      "RFC 4360: BGP Extended Communities Attribute
       RFC 4364: BGP/MPLS IP Virtual Private Networks (VPNs) §4.2
       RFC 5668: 4-Octet AS Specific BGP Extended Community";
  }

  grouping bgp-vrf-neighbor {
    description
      "Minimal per-peer attribute set for a CE peer configured under
       a `router bgp { vrf X }` block. Deliberately a small subset
       of `ietf-bgp:neighbor` — the per-VRF runtime that consumes
       these in step 13+ only needs the CE-attaching attributes, and
       the full attribute matrix continues to live on the top-level
       (global) neighbor list. The `peer-group` reference is a plain
       string so the block is parse-valid before its referenced
       neighbor-group has committed.";
    list neighbor {
      ext:help "BGP CE peer attached to this VRF";
      key "remote-address";
      description
        "List of BGP CE peers attached to this VRF.";
      leaf remote-address {
        ext:help "Remote CE peer IP address";
        type inet:ip-address;
        description
          "Remote peer IP address. Same address MUST NOT appear in
           more than one VRF — `commit` rejects the conflict, and
           the passive-accept dispatcher in step 16 relies on this
           uniqueness to route inbound :179 connections to the right
           VRF task.";
      }
      leaf remote-as {
        ext:help "Remote peer autonomous system number";
        type inet:as-number;
        description
          "AS number of the remote peer. When unset, the value
           inherited from the referenced `neighbor-group` applies.";
      }
      leaf neighbor-group {
        ext:help "Neighbor-group to inherit attributes from";
        type string;
        description
          "Name of a `neighbor-group` whose attributes this neighbor
           inherits. Same spelling as the global neighbor's
           `neighbor-group` leaf, and resolves against the same
           `router bgp neighbor-group <name>` list. Plain string (not
           leafref) for staging.";
      }
      leaf description {
        ext:help "Free-form neighbor description";
        // The pattern makes the value consume the rest of the command
        // line, whitespace included (`match_regexp` in config/parse.rs)
        // — same rest-of-line semantics as the global neighbor's
        // description leaf in ietf-bgp-common.
        type string {
          pattern '.*';
        }
        description
          "Free-form description string echoed in `show bgp vrf X
           neighbors` output. May contain spaces: the value is the
           rest of the line.";
      }
      container timers {
        ext:help "Per-neighbor BGP timers";
        description
          "Session timers for this CE peer. Deliberately NOT `uses
           neighbor-group-timers` (the grouping the global neighbor
           takes): two of that grouping's leaves (originate-interval,
           delay-open-time) are staged onto `PeerConfig::timer` and
           never read by any timer-arming path, so mirroring it here
           would expose knobs that silently do nothing. Only the leaves
           `crate::bgp::timer::Config` actually consumes are modelled.

           These are applied by `materialize_peers` when the peer is
           built, so an edit takes effect on the next VRF respawn or
           `clear bgp` rather than on the live session.

           `advertisement-interval` IS modelled here (unlike
           originate-interval / delay-open-time): it is the only way to
           set a per-VRF neighbor's MRAI, since the instance-level
           `router bgp timer adv-interval` snapshot does not reach
           per-VRF tasks. Without it a per-VRF session runs the stock
           30s eBGP / 5s iBGP MRAI.";
        leaf advertisement-interval {
          ext:help "MinRouteAdvertisementInterval (MRAI) in seconds";
          type uint16;
          units "seconds";
          description
            "Per-neighbor MRAI: how long the ipv4/ipv6-unicast
             advertise debounce coalesces burst route changes before
             flushing to this CE. `0` disables the debounce (the group
             flushes on the next event-loop tick). When unset the peer
             uses the stock default (30s eBGP / 5s iBGP), as the
             instance-level `router bgp timer adv-interval` does not
             reach the per-VRF task.";
          reference
            "RFC 4271: A Border Gateway Protocol 4 (BGP-4),
             Section 9.2.1.1.";
        }
        leaf connect-retry-time {
          ext:help "ConnectRetry timer (seconds)";
          type uint16 {
            range "1..max";
          }
          units "seconds";
          description
            "Time interval for the ConnectRetryTimer, pacing the
             Connect/Active redial loop. Defaults to 30s when unset —
             RFC 4271 §10 suggests 120s, but that is a suggestion and
             two minutes is a long outage for a session that is only
             waiting to redial; 30s matches FRR.";
          reference
            "RFC 4271: A Border Gateway Protocol 4 (BGP-4),
             Section 8.2.2.";
        }
        leaf hold-time {
          ext:help "Hold timer negotiated with the peer (seconds)";
          type uint16 {
            range "0 | 3..65535";
          }
          units "seconds";
          description
            "Hold Time proposed in this session's OPEN; the session
             uses the smaller of this and the peer's. Must be 0 or at
             least 3. Defaults to 180s when unset.";
          reference
            "RFC 4271: A Border Gateway Protocol 4 (BGP-4),
             Section 4.2.";
        }
        leaf idle-hold-time {
          ext:help "IdleHold timer before reconnect (seconds)";
          type uint16 {
            range "0..max";
          }
          units "seconds";
          description
            "Time the FSM dwells in Idle before the automatic restart
             re-arms the connect. Defaults to 5s when unset.";
        }
      }

      // Transport / session knobs, same names and types as the global
      // neighbor. Each stages onto the peer's `knobs_explicit` and is
      // resolved (explicit-wins-else-neighbor-group-else-default) and
      // applied by `materialize_peers` via the shared `apply_*`
      // functions, so a change takes effect on the next VRF respawn.
      // The remaining inheritable knobs the global neighbor carries
      // (allowas-in, as-override, enforce-first-as, remove-private-as,
      // route-reflector) are still inherited from a referenced
      // neighbor-group; exposing them as per-neighbor leaves is a
      // follow-up.
      container transport {
        ext:help "Transport (TCP) session parameters";
        leaf passive-mode {
          ext:help "Do not actively connect; wait for the peer to dial";
          type boolean;
          description
            "When true, this router never opens the connection to the
             CE; it only accepts an inbound one. Same as the global
             neighbor's transport/passive-mode.";
        }
      }
      leaf update-source {
        ext:help "Source address to bind for the outbound TCP connect";
        type inet:ip-address;
        description
          "Local IP address to bind before the outbound connect to this
           CE. Same as the global neighbor's update-source.";
      }
      leaf ebgp-multihop {
        ext:help "Allow an eBGP CE up to N hops away (TTL 1-255)";
        type uint8 {
          range "1..255";
        }
        description
          "Egress TTL for a multihop eBGP CE session. Ignored for iBGP.
           Mutually exclusive with ttl-security — the resolver applies
           ebgp-multihop first so the ttl-security guard sees it, matching
           the global neighbor.";
      }
      container ttl-security {
        ext:help "Enable GTSM: require a directly-connected CE (TTL 255)";
        presence "Enable GTSM for this CE neighbor";
        description
          "GTSM (RFC 5082): send at TTL 255 and accept only TTL-255
           inbound. Presence flag, mutually exclusive with
           ebgp-multihop. Same as the global neighbor.";
      }
      leaf port {
        ext:help "TCP port to dial this CE (default 179)";
        type uint16 {
          range "1..65535";
        }
        description
          "Destination port for the active connect toward this CE.
           Default 179. Same as the global neighbor's port.";
      }
      container ip-transparent {
        ext:help "Bind a local address the host does not own";
        presence "Set IP_TRANSPARENT on this CE's TCP socket";
        description
          "Set IP_TRANSPARENT / IPV6_TRANSPARENT so the session can bind
           a non-local `update-source` address. Same as the global
           neighbor; applied on connect only when update-source is set.";
      }
      container disable-connected-check {
        ext:help "Allow a single-hop eBGP CE off-subnet";
        presence "Skip the directly-connected-network check for this CE";
        description
          "Skip the directly-connected-network check for a single-hop
           eBGP CE (e.g. a CE loopback reachable via a static route),
           leaving the egress TTL at 1. Same as the global neighbor.";
      }

      // The remaining inheritable knobs, same names / types / shapes as
      // the global neighbor. Each stages onto knobs_explicit and is
      // resolved (explicit-else-neighbor-group-else-default) and applied
      // by materialize_peers via apply_inherited_session_knobs; the two
      // structured ones share the global neighbor's staging state
      // machine (InheritableKnobs::stage_*). A change takes effect on the
      // next VRF respawn.
      container as-override {
        ext:help "Replace the CE's AS in the outbound AS_PATH";
        presence "Enable as-override toward this CE";
        description
          "Replace every occurrence of this CE's AS in the outbound
           AS_PATH with the local AS (before the local-AS prepend). No-op
           for iBGP. Same as the global neighbor.";
      }
      container enforce-first-as {
        ext:help "Require inbound AS_PATH to start with the CE's AS";
        presence "Enable the first-AS check on inbound updates from this CE";
        description
          "Drop an inbound eBGP UPDATE unless the left-most AS_PATH
           segment begins with the CE's own AS. No-op for iBGP. Same as
           the global neighbor.";
      }
      container route-server-client {
        ext:help "Treat this CE as a route-server client (RFC 7947)";
        presence "Advertise routes to this CE transparently, as a route server";
        description
          "Keep the AS_PATH (no local-AS prepend) and the received
           NEXT_HOP on routes advertised to this eBGP CE. No-op for
           iBGP. Same as the global neighbor (zebra-bgp-route-server.yang).";
      }
      list otc-local-role {
        key "role";
        max-elements 1;
        ext:help "RFC 9234 BGP Role toward this CE (route-leak prevention)";
        description
          "RFC 9234 local BGP Role for this eBGP session, IOS XR
           `otc-local-role` syntax. Single-instance. Same as the global
           neighbor (zebra-bgp-otc.yang).";
        leaf role {
          ext:help "Local role: customer, provider, peer, route-server-client or route-server";
          type enumeration {
            enum customer;
            enum provider;
            enum peer;
            enum route-server-client;
            enum route-server;
          }
        }
        leaf strict {
          ext:help "Require the CE to send its BGP Role (strict mode)";
          type empty;
          description
            "Reject the session with a Role Mismatch NOTIFICATION when
             the CE sends no BGP Role capability.";
        }
      }
      container route-reflector {
        ext:help "Route-reflector settings for this CE";
        leaf client {
          ext:help "Treat this CE as a route-reflector client";
          type boolean;
          default "false";
          description
            "Configure the CE as a route-reflector client (RFC 4456).
             Same as the global neighbor's route-reflector/client.";
        }
      }
      container allowas-in {
        ext:help "Accept routes containing our own AS in the AS_PATH";
        presence "Enable allowas-in (default occurrence count 3)";
        description
          "Relax the inbound AS_PATH loop check for this CE. Bare form
           accepts up to 3 occurrences of the local AS. Same choice
           shape as the global neighbor.";
        choice mode {
          description "Occurrence budget, or origin-only. Mutually exclusive.";
          case count {
            leaf count {
              ext:help "Max times our AS may appear in AS_PATH (default 3)";
              type uint8 {
                range "1..10";
              }
              default "3";
              description "Accept while the local AS appears at most this many times.";
            }
          }
          case origin {
            leaf origin {
              ext:help "Accept the local AS only at the route origin";
              type empty;
              description
                "Accept only when the local AS is solely the originating AS.";
            }
          }
        }
      }
      container remove-private-as {
        ext:help "Remove private ASNs from the outbound AS_PATH";
        presence "Enable remove-private-as toward this CE";
        description
          "Strip private ASNs from the outbound AS_PATH toward this CE
           (bare form acts only on an all-private path). Same modifier
           leaves as the global neighbor.";
        leaf all {
          ext:help "Remove private ASNs from a mixed AS_PATH";
          type empty;
          description "Act on any AS_PATH containing a private AS, not only an all-private one.";
        }
        leaf replace-as {
          ext:help "Replace private ASNs with the local AS";
          type empty;
          description "Rewrite each stripped private AS to the local AS, keeping path length.";
        }
      }

      container bfd {
        ext:help "BFD attachment for this CE (single-hop only)";
        description
          "Per-VRF BFD is SINGLE-HOP ONLY. The BFD SessionKey carries no
           VRF/table dimension and the daemon's socket is not VRF-bound,
           so a session is disambiguated and made reachable purely by the
           directly-connected CE's egress ifindex. Multihop (ifindex 0)
           would conflate overlapping-address VRFs and cannot egress a
           VRF-only route, so the `multihop` leaf is refused at commit.
           `minimum-ttl` (multihop only) is deliberately absent.

           On a BFD-down the CE's BGP session is torn down (RFC 5882 §5).
           There is no per-VRF instance-level `bfd {}` default, so each
           leaf resolves over the built-in default (BFD off unless
           `enabled true`).";
        leaf enabled {
          ext:help "Activate BFD for this CE";
          type boolean;
          description "Bring up a single-hop BFD session to this CE. Absent ⇒ off.";
        }
        // NB: no `multihop` / `minimum-ttl` leaves. Per-VRF BFD is
        // single-hop only, and a config callback cannot fail a commit
        // (`Bgp::process_cm_msg` discards the callback's return), so an
        // accept-then-warn leaf would report "applied" while silently
        // ignoring the value. Omitting the leaf makes `bfd multihop …`
        // fail YANG validation instead — a real rejection.
        leaf echo-mode {
          ext:help "BFD Echo role (transmit | receive | both)";
          type enumeration {
            enum transmit { description "Originate Echo only."; }
            enum receive { description "Advertise + reflect only."; }
            enum both { description "Both."; }
          }
          description "BFD Echo function (RFC 5880 §6.4). Same values as the global neighbor.";
        }
        leaf echo-transmit-interval {
          ext:help "Echo transmit interval (ms)";
          type uint32;
          units "milliseconds";
          description "Rate we originate Echo at. Default 50ms when unset.";
        }
        leaf echo-receive-interval {
          ext:help "Advertised Required Min Echo RX Interval (ms)";
          type uint32;
          units "milliseconds";
          description "Advertised Required Min Echo RX. Default 50ms when unset.";
        }
        leaf detect-offload {
          ext:help "Offload expiration detection to the XDP data plane";
          type boolean;
          description "Detect missing control packets in the kernel XDP data plane. Absent ⇒ userspace.";
        }
      }

      leaf password {
        ext:help "Shared TCP-MD5 secret for this CE (RFC 2385)";
        type string {
          length "1..80";
        }
        description
          "TCP-MD5 secret for the PE-CE session, same shape as the global
           neighbor's `password`. Applied to BOTH directions: the
           VRF-bound connect socket (PE-initiated dial) and this VRF's own
           VRF-bound listener socket (CE-initiated inbound), so the session
           authenticates whichever side connects. Overlapping-address VRFs
           do not collide — each VRF has its own listener socket with its
           own per-address key.";
      }

      container tcp-ao {
        ext:help "TCP Authentication Option (RFC 5925)";
        presence "Enable TCP-AO on this CE";
        description
          "TCP-AO for the PE-CE session, same shape as the global
           neighbor. Applied to both directions — the VRF-bound connect
           socket and this VRF's own VRF-bound listener MKT — so the
           session authenticates whichever side initiates.

           The key-chain is resolved through the policy actor (the CE
           peer's per-VRF task subscribes under `bgp-vrf:<name>`), so an
           in-chain key rotation propagates without a reconfig, and a
           resolved key is re-installed on the listener as it changes.";
        reference "RFC 5925, RFC 5926";
        leaf key-chain {
          ext:help "Key chain name";
          type string;
          mandatory true;
          description
            "Name of a key chain under /key-chains. Existence is not
             enforced by the schema; an unresolved chain simply yields no
             key (the dial goes out unauthenticated) until it appears.";
        }
        leaf include-tcp-options {
          ext:help "Include TCP options in MAC";
          type boolean;
          default "true";
          description
            "If true (default) the TCP-AO MAC covers other TCP options;
             false covers only the fixed header + data. Both endpoints
             MUST agree. Same as the global neighbor.";
          reference "RFC 5925 §3.1";
        }
      }
      list afi-safi {
        ext:help "Per-address-family activation for this CE peer";
        key "name";
        description
          "Per-address-family activation for this CE peer — the
           equivalent of IOS-XR `address-family <af> ... neighbor X
           activate`. An entry with `enabled true` adds the family to
           the Multiprotocol capability set advertised in the OPEN;
           `enabled false` removes it. Only the IPv4 and IPv6 unicast
           families apply to a PE-CE session (VPNv4 / VPNv6 / EVPN stay
           anchored on the top-level / global neighbor list).

           When no entry is present the negotiated family is derived
           from the peer's own address: an IPv6 CE peer exchanges IPv6
           unicast, an IPv4 CE peer IPv4 unicast — so the common
           single-family deployment needs no statement here. The
           explicit knob is only required to override that, e.g. to
           additionally carry IPv4 unicast over an IPv6 session. Unlike
           the global neighbor, IPv4 unicast is NOT forced on for an
           IPv6 peer. A change takes effect when the session next
           renegotiates capabilities (`clear bgp`).";
        uses zas:afi-safi-unicast;
        leaf enabled {
          ext:help "Enable this address family for the CE peer";
          type boolean;
          mandatory true;
          description
            "Whether this AFI,SAFI is enabled for the CE peer.";
        }

        // The knobs below mirror the global neighbor's
        // /router/bgp/neighbor/afi-safi subtree leaf for leaf, and share
        // its setters (src/bgp/afi_knob.rs) so the two can never diverge
        // in meaning. `vrf_afi_knob_parity` in src/config/manager.rs
        // pins the *set* of knobs: adding one to the global neighbor
        // without adding it here (or listing it as a deliberate
        // exclusion) fails that test.
        //
        // Unlike the global neighbor these are staged, not applied to a
        // live peer — a CE peer runs in the per-VRF task, out of reach
        // of a config callback — so an edit takes effect on the next VRF
        // respawn or `clear bgp`.
        // Per-AFI knobs shared verbatim with the global neighbor via one
        // grouping, so the two subtrees cannot diverge in leaf TYPE the
        // way they once did (both enum leaves were hand-copied as `type
        // string`, which nothing caught — `vrf_afi_knob_parity` compares
        // the knob set, not types, and a setter's rejection is never
        // reported because `Bgp::process_cm_msg` discards the callback's
        // return value).
        //
        // `graceful-restart` below stays local: the global container's
        // `enabled` comes from mp-afi-safi-graceful-restart-config, whose
        // `must` path is anchored to the global neighbor's tree depth and
        // would be wrong here.
        //
        // Unlike the global neighbor these are staged, not applied to a
        // live peer — a CE peer runs in the per-VRF task, out of reach of
        // a config callback — so an edit takes effect on the next VRF
        // respawn or `clear bgp`.
        uses zbak:bgp-neighbor-afi-knobs;

        container graceful-restart {
          ext:help "Per-family Graceful Restart (RFC 4724)";
          leaf enabled {
            ext:help "Advertise GR forwarding-state preservation";
            type boolean;
          }
        }
      }
    }
  }

  grouping bgp-vrf-redistribute {
    description
      "Per-VRF, per-AFI redistribution of RIB routes into this VRF's
       BGP table. A source's routes are taken from the VRF's own
       routing table (`vrf_tables[table_id]`, never the default
       table), originated into the per-VRF Loc-RIB, and exported to
       the global VPNv4 / VPNv6 RIB with the VRF's RD and export
       route-targets — the standard IOS-XR `router bgp … vrf …
       address-family … redistribute …` model.

       Bare presence containers (no per-source modifiers yet); the
       redistributed route's MED follows the source RIB cost. The IGP
       sources pull this VRF's OSPF / IS-IS routes — which a per-VRF
       OSPF / IS-IS instance installs into `vrf_tables[table_id]` — so
       a PE can advertise CE-learned IGP routes into the VPN without a
       per-source level / match filter (deferred with the other
       modifiers).";
    container redistribute {
      ext:help "Redistribute RIB routes into this VRF's BGP";
      // A bare `redistribute` with no source child enables nothing:
      // reject it at commit and prune the container when its last
      // source is deleted (ext:non-empty on a presence container).
      ext:non-empty "kernel, connected, static, ospf or isis";
      presence "Enable route redistribution into this VRF's BGP table";
      container kernel {
        ext:help "Redistribute this VRF's kernel routes";
        presence "Redistribute this VRF's kernel routes";
      }
      container connected {
        ext:help "Redistribute this VRF's connected routes";
        presence "Redistribute this VRF's connected routes";
      }
      container static {
        ext:help "Redistribute this VRF's static routes";
        presence "Redistribute this VRF's static routes";
      }
      container ospf {
        ext:help "Redistribute this VRF's OSPF routes";
        presence "Redistribute this VRF's OSPF routes";
      }
      container isis {
        ext:help "Redistribute this VRF's IS-IS routes";
        presence "Redistribute this VRF's IS-IS routes";
      }
    }
  }

  grouping bgp-vrf-afi-safi {
    description
      "Per-VRF address-family configuration. Only the IPv4 and IPv6
       unicast families are exposed here — VPNv4 / VPNv6 / EVPN
       advertisements remain anchored on the top-level `router bgp`
       block and are driven by the cross-VRF import/export pipeline.

       The family names match the IS-IS afi-safi convention (`ipv4`,
       `ipv6`) so a VRF reads the same as `router isis`; modeled as a
       container of two presence containers (one per family) for
       path-based config ergonomics (`set ... afi-safi ipv4 ...`).";
    container afi-safi {
      ext:help "Per-VRF address-family configuration";
      container ipv4 {
        ext:help "Enable the IPv4 unicast family for this VRF";
        presence "Enables the IPv4 unicast family for this VRF";
        list network {
          ext:help "Network prefix to originate into VPNv4";
          key "prefix";
          description
            "Configured network the VRF should originate as a BGP
             route into the global VPNv4 RIB (after best-path inside
             the VRF). Same semantics as the IS-IS network leaf and
             the top-level BGP network knob.";
          leaf prefix {
            ext:help "IPv4 network prefix";
            type inet:ipv4-prefix;
          }
        }
        uses bgp-vrf-redistribute;
      }
      container ipv6 {
        ext:help "Enable the IPv6 unicast family for this VRF";
        presence "Enables the IPv6 unicast family for this VRF";
        list network {
          ext:help "Network prefix to originate into VPNv6";
          key "prefix";
          leaf prefix {
            ext:help "IPv6 network prefix";
            type inet:ipv6-prefix;
          }
        }
        uses bgp-vrf-redistribute;
      }
      container mup {
        ext:help "Per-VRF MUP (Mobile User Plane) service";
        description
          "Per-VRF MUP (draft-ietf-bess-mup-safi) service. The `segment` list is the PE
           side: `segment direct` originates a Direct Segment Discovery
           (DSD, type 2) route for this VRF carrying the VRF's End.DT46
           SID (carved from `encapsulation srv6`); `segment interwork` an
           Interwork Segment Discovery (ISD, type 1) route. The `route`
           list is the controller side: `route {st1|st2}` binds a PFCP
           session Network Instance to Session-Transformed (ST) route
           origination. A receiving PE derives forwarding for matching ST
           routes from the segment routes (draft-ietf-bess-mup-safi
           default).";
        leaf dataplane {
          ext:help "MUP forwarding-plane behaviour for this VRF";
          type enumeration {
            enum end-dt46 {
              description
                "SRv6 End.DT46, the mainline-kernel stand-in: a resolved ST
                 route installs a seg6local End.DT46 decap plus an SRv6
                 H.Encaps toward the segment SID. The GTP-U TEID rides the
                 control plane only. Works on stock Linux. This is the
                 default.";
            }
            enum gtp {
              description
                "Real GTP-U: install the tunnel from the ST route's endpoint
                 and TEID via the cradle eBPF forwarder (GTP4.E downlink /
                 H.M.GTP4.D uplink). Requires `system cradle enabled` to tee
                 into the forwarder (`system cradle grpc-endpoint` only
                 overrides where it is); the mainline kernel has no GTP
                 action.";
            }
          }
          default end-dt46;
          description
            "MUP forwarding-plane behaviour for this VRF: the SRv6 End.DT46
             stand-in (mainline kernel) or real GTP-U (cradle eBPF). The
             control plane is identical either way — this selects only the
             endpoint behaviour advertised and whether the FIB install targets
             the kernel seg6local or the cradle GTP maps.";
        }
        list segment {
          ext:help "MUP Segment Discovery route to originate";
          key "type";
          description
            "MUP Segment Discovery route type originated for this VRF.
             `segment direct` originates a Direct Segment Discovery (DSD,
             type 2) route carrying the VRF's End.DT46 SID; `segment
             interwork` an Interwork Segment Discovery (ISD, type 1)
             route. The `direct` entry additionally carries the
             `mup-ext-comm` identifying this VRF's Direct segment.";
          leaf type {
            ext:help "Segment Discovery type (direct | interwork)";
            type enumeration {
              enum direct {
                description
                  "Originate a Direct Segment Discovery (DSD, type 2)
                   route: the NLRI is the VRF RD + router-id and the SRv6
                   L3 Service carries the per-VRF End.DT46 SID.";
              }
              enum interwork {
                description
                  "Originate an Interwork Segment Discovery (ISD, type 1)
                   route: the NLRI is the VRF RD + the configured `prefix`
                   and the SRv6 L3 Service carries the per-VRF End.DT46 SID.
                   Requires `prefix` to be set.";
              }
            }
            description
              "MUP Segment Discovery route type originated for this VRF.";
          }
          leaf mup-ext-comm {
            ext:help "MUP Extended Community for the Direct segment";
            type route-distinguisher;
            description
              "BGP MUP Extended Community (transitive type 0x0c, sub-type
               0x00 = Direct-Type Segment Identifier,
               draft-mpmz-bess-mup-safi §3.2) identifying this VRF's Direct
               segment. Attached to the VRF's Direct Segment Discovery (DSD)
               route and to the controller's Type-2 Session-Transformed
               (ST2) routes that resolve to this Direct segment (§3.3.10 /
               §3.3.12). The 6-octet value reuses the RD/RT 2:4 wire format.
               Meaningful only under the `direct` segment.";
          }
          leaf prefix {
            ext:help "Interwork segment prefix for the ISD route";
            type inet:ip-prefix;
            description
              "Interwork segment prefix advertised in the Interwork Segment
               Discovery (ISD, type 1) route's NLRI
               (draft-mpmz-bess-mup-safi §3.1.1) — typically the locally
               connected gNodeB N3 interface prefix. The route's AFI follows
               this prefix's family (IPv4 / IPv6) and the SRv6 L3 Service
               carries the VRF's End.DT46 SID. Meaningful only under the
               `interwork` segment; the ISD does not originate until it is
               set.";
          }
          leaf lookup-network-instance {
            ext:help "VRF the GTP-side (N3) lookup runs in for this interwork segment";
            type string;
            description
              "Names the VRF that is the GTP-side routing context for this
               interwork segment, when it is not the declaring VRF itself.
               With `dataplane gtp` the declaring VRF's ST1 endpoints
               (falling inside `prefix`) resolve their post-encap outer
               (gw, oif) in the named VRF's table, and its ST2 decap PDRs
               match G-PDUs arriving on the named VRF's ports — the
               split/GTP-gateway shape where the service VRF advertises the
               downlink entry point (its own DT SID) while GTP-U rides a
               separate N3 VRF. Defaults to the declaring VRF. Meaningful
               only under the `interwork` segment.";
          }
        }
        list route {
          ext:help "Session-Transformed (ST) route to originate";
          key "type";
          description
            "Session-Transformed route origination for this VRF, keyed by
             ST route type. `route st1` is the downlink (Type-1 ST / N6;
             ingress GTP encapsulation); `route st2` the uplink (Type-2 ST
             / N3; egress GTP decapsulation). Each binds the PFCP session
             Network Instance whose sessions the MUP controller originates
             ST routes for; `route st2` additionally carries its own
             `mup-ext-comm` of the Direct segment those ST2 routes resolve
             to.";
          leaf type {
            ext:help "ST route type (st1 downlink | st2 uplink)";
            type enumeration {
              enum st1 {
                description
                  "Type-1 ST (downlink); ingress GTP encapsulation, the
                   N6 VRF.";
              }
              enum st2 {
                description
                  "Type-2 ST (uplink); egress GTP decapsulation, the
                   N3 VRF.";
              }
            }
            description
              "ST route type this entry originates (st1 = downlink / N6,
               st2 = uplink / N3).";
          }
          leaf network-instance {
            ext:help "PFCP session Network Instance to match";
            type string;
            description
              "PFCP session Network Instance whose sessions this VRF
               originates ST routes for. When the MUP controller learns a
               session whose Network Instance matches this value, it
               originates the ST route (st1 → Type-1 / ingress encap;
               st2 → Type-2 / egress decap into the VRF's End.DT46 Direct
               segment).";
          }
          leaf mup-ext-comm {
            ext:help "Direct-segment MUP Ext Comm for ST2 routes";
            type route-distinguisher;
            description
              "BGP MUP Extended Community (Direct-Type Segment Identifier,
               draft-mpmz-bess-mup-safi §3.2 / §3.3.10) of the Direct
               segment the originated ST2 routes resolve to, so a receiving
               PE maps the (endpoint, TEID) tunnel onto the matching
               End.DT46 segment. Meaningful only under `route st2`. The
               6-octet value reuses the RD/RT 2:4 wire format.";
          }
        }
      }
    }
  }

  grouping bgp-vrf-extension {
    description
      "Per-VRF BGP block hung off the top-level `router bgp` tree.";
    list vrf {
      ext:help "Per-VRF BGP context";
      key "name";
      description
        "Per-VRF BGP context. The VRF name is a plain string and need
         not yet be declared at the top-level /vrf list when this
         config is parsed — same staging pattern as IS-IS uses for
         `block` and `locator`.";
      leaf name {
        ext:help "VRF name this BGP block applies to";
        ext:dynamic "rib:vrf";
        type string;
        description
          "Name of the VRF this BGP block applies to.";
      }
      leaf rd {
        ext:help "Route Distinguisher for this VRF's VPN routes";
        type route-distinguisher;
        description
          "Route Distinguisher prepended to VPNv4 / VPNv6 NLRIs
           originating from this VRF. See RFC 4364 §4.2.";
      }
      leaf router-id {
        ext:help "Per-VRF BGP router-id (overrides global)";
        type inet:ipv4-address;
        description
          "Per-VRF BGP router-id. Overrides the global router-id
           for VPNv4 / VPNv6 NLRIs sourced from this VRF and for
           the OPEN exchange with CE peers attached here. When
           unset, the top-level `router bgp global identifier`
           value applies — same fallback Cisco IOS-XR uses.";
      }
      leaf label-mode {
        ext:help "VPN label allocation strategy for this VRF";
        type enumeration {
          enum per-vrf {
            description
              "One MPLS label per VRF (default). All VPN routes
               leaving this VRF carry the same label; the PE pops
               and forwards via the VRF master device. Lowest label
               churn and the safest default for a first per-VRF
               BGP deployment.";
          }
          enum per-route {
            description
              "One MPLS label per advertised prefix. Decoupled from
               next-hop changes, but produces O(prefix) labels per
               VRF — only enable when downstream policy needs it.";
          }
          enum per-nexthop {
            description
              "One MPLS label per (VRF, BGP next-hop) tuple.
               Common middle ground between per-vrf and per-route
               for VRFs with multiple distinct exit points.";
          }
        }
        default "per-vrf";
        description
          "Label allocation strategy for VPN routes originated from
           this VRF. Consulted by the label allocator in step 19.";
      }
      leaf encapsulation {
        ext:help "VPN data-plane encapsulation (mpls | srv6)";
        type enumeration {
          enum mpls {
            description
              "MPLS encapsulation (default, RFC 4364). VPN routes
               carry an MPLS service label and a PE pops it into the
               VRF master device.";
          }
          enum srv6 {
            description
              "SRv6 encapsulation (RFC 9252). The VRF binds a single
               End.DT46 service SID carved from the global `srv6
               locator`, advertised in the BGP Prefix-SID attribute;
               the PE decapsulates into the VRF table via seg6local.
               Requires a resolved global `srv6 locator`.";
          }
          enum vxlan {
            description
              "VXLAN symmetric-IRB encapsulation (RFC 9135 / RFC 8365).
               EVPN Type-5 routes carry the tenant L3VNI in the NLRI
               label field and this PE's router-MAC in the Router's-MAC
               extended community; the ingress PE VXLAN-encapsulates the
               inner IP toward the egress VTEP and rewrites the inner
               Ethernet with the remote router-MAC. Requires the VRF's
               `evpn l3vni` and `evpn router-mac` to be set.";
          }
        }
        default "mpls";
        description
          "VPN data-plane encapsulation for routes originated from /
           imported into this VRF.";
      }
      leaf inter-as-hybrid {
        ext:help "RFC 4364 Inter-AS VPN Option AB re-export";
        type boolean;
        default "false";
        description
          "RFC 4364 Inter-AS MPLS/VPN Option AB. When true, this VRF
           re-exports the VPNv4 routes it imports (not only `network`/
           CE-learned routes) back into the global VPNv4 table. An ASBR
           configured this way relays a remote AS's VPN routes to its own
           PEs (and the peer ASBR) over a single MP-eBGP VPNv4 session,
           while the VPN label still terminates at the ASBR and the
           packet is forwarded per-VRF (combining the per-VPN control of
           Option A with the single-session scale of Option B). The
           re-import loop is broken by excluding the originating VRF from
           the import fan-out and by eBGP AS-path. Default false leaves an
           ordinary intra-AS L3VPN VRF unchanged.";
      }
      container evpn {
        ext:help "EVPN Type-5 (IP Prefix) service for this VRF";
        description
          "EVPN (RFC 9136 Type-5 / IP Prefix) service for this VRF.
           When advertise-ipv4 / advertise-ipv6 is enabled, the VRF's
           IPv4 / IPv6 unicast routes are additionally advertised as
           EVPN Type-5 (IP Prefix) routes carrying the per-VRF RD,
           export route-targets and encapsulation (MPLS service label
           or SRv6 End.DT46 SID) — the same per-VRF state already used
           for VPNv4 / VPNv6. A peer receives Type-5 only if it
           negotiated the L2VPN/EVPN AFI/SAFI, so this composes with
           VPNv4/VPNv6 rather than replacing it. Named to match the
           `evpn` family in zebra-afi-safi.yang.";
        leaf advertise-ipv4 {
          ext:help "Advertise IPv4 routes as EVPN Type-5";
          type boolean;
          default false;
          description
            "Advertise this VRF's IPv4 unicast routes as EVPN Type-5
             (IP Prefix) routes. Requires `rd` to be set.";
        }
        leaf advertise-ipv6 {
          ext:help "Advertise IPv6 routes as EVPN Type-5";
          type boolean;
          default false;
          description
            "Advertise this VRF's IPv6 unicast routes as EVPN Type-5
             (IP Prefix) routes. Requires `rd` to be set.";
        }
        leaf l3vni {
          ext:help "Tenant L3VNI for VXLAN symmetric-IRB Type-5";
          type uint32 {
            range "1..16777215";
          }
          description
            "L3VNI carried in the EVPN Type-5 NLRI label field when
             `encapsulation vxlan` is set. Identifies the tenant VRF
             on the egress PE for symmetric IRB (RFC 8365). Must match
             an `l3vni` on a local `vxlan` device bound to this VRF.";
        }
        leaf router-mac {
          ext:help "Router-MAC advertised in EVPN Type-5 (VXLAN IRB)";
          type yang:mac-address;
          description
            "This PE's router-MAC, advertised in the Router's-MAC
             extended community (RFC 9135) on VXLAN Type-5 routes. The
             ingress PE rewrites the inner Ethernet destination with the
             egress PE's router-MAC before VXLAN encapsulation. Defaults
             to the VRF master device MAC when unset.";
        }
      }
      uses bgp-vrf-neighbor;
      uses bgp-vrf-afi-safi;
    }
  }

  /* =========================================================
   * Augments into the zebra-rs configure tree
   * ========================================================= */

  augment "/configure:set/config:router/bgp:bgp" {
    description
      "Attach the per-VRF list to `router bgp` in the candidate-set
       subtree.";
    uses bgp-vrf-extension;
  }

  augment "/configure:delete/config:router/bgp:bgp" {
    description
      "Same attachment for the delete subtree so
       `delete router bgp vrf X rd` is path-valid.";
    uses bgp-vrf-extension;
  }
}

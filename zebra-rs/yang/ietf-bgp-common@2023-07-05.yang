submodule ietf-bgp-common {
  yang-version 1.1;
  belongs-to ietf-bgp {
    prefix bgp;
  }

  import iana-bgp-types {
    prefix bt;
    reference
      "RFC XXXX: YANG Model for Border Gateway Protocol (BGP-4).";
  }
  import iana-bgp-community-types {
    prefix bct;
    reference
      "RFC XXXX: YANG Model for Border Gateway Protocol (BGP-4).";
  }
  import ietf-interfaces {
    prefix if;
    reference
      "RFC 7223: A YANG Data Model for Interface Management.";
  }
  import ietf-key-chain {
    prefix key-chain;
    reference
      "RFC 8177: YANG Data Model for Key Chains.";
  }
  import ietf-inet-types {
    prefix inet;
    reference
      "RFC 6991: Common YANG Data Types.";
  }
  import ietf-routing-policy {
    prefix rt-pol;
    reference
      "RFC 9067: A YANG Data Model for Routing Policy.";
  }
  import ietf-yang-types {
    prefix yang;
    reference
      "RFC 6991: Common YANG Data Types.";
  }
  import ietf-bfd-types {
    prefix bfd-types;
    reference
      "RFC 9127: YANG Data Model for Bidirectional Forward
       Detection.";
  }
  import ietf-tcp {
    prefix tcp;
    reference
      "I-D.ietf-tcpm-yang-tcp: Transmission Control Protocol (TCP)
       YANG Model.";
  }
  import extension {
    prefix ext;
  }
  include ietf-bgp-common-structure {
    revision-date 2023-07-05;
  }

  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com,
              Jeffrey Haas (jhaas at juniper.net).";

  description
    "This sub-module contains common groupings that are common across
     multiple contexts within the BGP module. That is to say that
     they may be application to a subset of global, peer-group, or
     neighbor contexts.

     Copyright (c) 2023 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2023-07-05 {
    description
      "Initial Version";
    reference
      "RFC XXXX: YANG Model for Border Gateway Protocol (BGP-4).";
  }

  grouping neighbor-group-timers {
    description
      "Config parameters related to timers associated with the BGP
       peer";
    leaf connect-retry-time {
      ext:help "ConnectRetry timer (seconds)";
      type uint16 {
        range "1..max";
      }
      units "seconds";
      default "120";
      description
        "Time interval (in seconds) for the ConnectRetryTimer. The
         suggested value for this timer is 120 seconds.";
      reference
        "RFC 4271: A Border Gateway Protocol 4 (BGP-4),
         Section 8.2.2.";
    }
    leaf hold-time {
      ext:help "Hold timer negotiated with the peer (seconds)";
      type uint16 {
        range "0 | 3..65535";
      }
      units "seconds";
      default "90";
      description
        "Time interval (in seconds) for the HoldTimer established
         with the peer.  When read as operational data (ro), the
         value of this object is calculated by this BGP speaker,
         using the smaller of the values in hold-time that was
         configured (rw) in the running datastore and the Hold Time
         received in the OPEN message.

         This value must be at least three seconds
         if it is not zero (0).
         If the Hold Timer has not been established
         with the peer this object MUST have a value
         of zero (0).

         If the configured value of hold-time object was
         a value of (0), then when read this object MUST have a
         value of (0) also.";
      reference
        "RFC 4271: A Border Gateway Protocol 4 (BGP-4), Section 4.2,
         RFC 4271: A Border Gateway Protocol 4 (BGP-4), Section 10.";
    }
    leaf negotiated-hold-time {
      type uint16;
      config false;
      description
        "The negotiated hold-time for the BGP session";
      reference
        "RFC 4271: A Border Gateway Protocol 4 (BGP-4), Section 4.2,
         RFC 4271: A Border Gateway Protocol 4 (BGP-4), Section 10.";
    }
    leaf idle-hold-time {
      ext:help "IdleHold timer before reconnect (seconds)";
      type uint16 {
        range "0..max";
      }
    }
    leaf delay-open-time {
      ext:help "DelayOpen timer (seconds)";
      type uint16 {
        range "0..max";
      }
    }
    leaf originate-interval {
      ext:help "Minimum AS-origination interval (seconds)";
      type uint16 {
        range "0..max";
      }
      units "seconds";
      description
        "Time interval (in seconds) for the MinASOriginationInterval
         timer. The suggested value for this timer is 15 seconds.";
      reference
        "RFC 4271: A Border Gateway Protocol 4 (BGP-4), Section
         9.2.1.2,
         RFC 4271: A Border Gateway Protocol 4 (BGP-4), Section 10.";
    }
    leaf advertisement-interval {
      ext:help "Minimum route advertisement interval (MRAI)";
      type uint16 {
        range "0..max";
      }
      units "seconds";
      description
        "Time interval (in seconds) for the
         MinRouteAdvertisementInterval timer.
         The suggested value for this timer is 30
         seconds for EBGP connections and 5
         seconds for IBGP connections.";
      reference
        "RFC 4271: A Border Gateway Protocol 4 (BGP-4), Section
         9.2.1.1,
         RFC 4271: A Border Gateway Protocol 4 (BGP-4), Section 10.";
    }
  }

  grouping neighbor-group-config {
    description
      "Neighbor level configuration items.";
    leaf remote-as {
      ext:help "Autonomous system number of the peer";
      type inet:as-number;
      description
        "AS number of the peer.";
    }
    // local-as: removed from the vendored IETF model so zebra-rs can
    // own the name as an FRR-style single-entry list keyed by the
    // substitute AS number (zebra-bgp-local-as.yang). The plain leaf
    // cannot carry the no-prepend / replace-as / dual-as modifiers,
    // and an augment can't add a same-named node over this leaf
    // (RFC 7950 §7.17). See the zebra module.
    //  leaf local-as {
    //    type inet:as-number;
    //  }
    // remove-private-as: removed from the vendored IETF model so
    // zebra-rs can own the name as an FRR-style presence container
    // (zebra-bgp-remove-private-as.yang). The IANA identityref typedef
    // (bt:remove-private-as-option) uses an unprefixed `base`, which this
    // libyang build cannot resolve to its value set, and an augment can't
    // add a same-named node over this leaf (RFC 7950 §7.17). zebra-rs does
    // not implement the IANA identityref form. See the zebra module.
    //  leaf remove-private-as {
    //    type bt:remove-private-as-option;
    //  }
    // route-flap-damping was removed from neighbor-group-config: it was an
    // unhandled orphan (no config handler) on every consumer of this
    // grouping and has been dropped.
    leaf description {
      ext:help "Free-form neighbor description";
      // The pattern makes the value consume the rest of the command
      // line, whitespace included (`match_regexp` in config/parse.rs)
      // — FRR's `neighbor X description LINE`. A pattern-less string
      // would stop at the first space.
      type string {
        pattern '.*';
      }
      description
        "Free-form description string echoed in `show bgp neighbors`
         output. May contain spaces: the value is the rest of the
         line.";
    }
    container timers {
      ext:help "Per-neighbor BGP timers";
      description
        "Timers related to a BGP neighbor";
      uses neighbor-group-timers;
    }

    container transport {
      ext:help "Transport (TCP) session parameters";
      description
        "Transport session parameters for the BGP neighbor";
      uses neighbor-group-transport-config;
    }

    uses structure-neighbor-group-route-reflector;
    // The peer-wide `neighbor X policy {in,out}` (rt-pol:apply-policy-group)
    // was retired; per-family route-policy now lives under
    // `neighbor X afi-safi <name> policy {in,out}` (ietf-bgp-neighbor).
  }

  grouping neighbor-group-transport-config {
    description
      "Configuration parameters relating to the transport protocol
       used by the BGP session to the peer.";

    leaf local-address {
      ext:help "Local address to bind for the BGP session";
      type union {
        type inet:ipv4-address;
        type inet:ipv6-address;
      }
      description
        "Set the local IP (either IPv4 or IPv6) address to use for
         the session when sending BGP update messages. This may be
         expressed as either an IP address or reference to the name
         of an interface.";
    }

    leaf passive-mode {
      ext:help "Wait for the peer to initiate the connection";
      type boolean;
      default "false";
      description
        "Wait for peers to issue requests to open a BGP session,
         rather than initiating sessions from the local router.";
    }

  }

  grouping global-group-use-multiple-paths {
    description
      "Common grouping used for both global and groups which provides
       configuration and state parameters relating to use of multiple
       paths";
    container use-multiple-paths {
      description
        "Parameters related to the use of multiple paths for the
         same NLRI";
      leaf enabled {
        type boolean;
        default "false";
        description
          "Whether the use of multiple paths for the same NLRI is
           enabled for the neighbor. This value is overridden by any
           more specific configuration value.";
      }
      container ebgp {
        description
          "Multi-Path parameters for eBGP";
        leaf allow-multiple-as {
          type boolean;
          default "false";
          description
            "Allow multi-path to use paths from different neighboring
             ASes.  The default is to only consider multiple paths
             from the same neighboring AS.";
        }
        leaf maximum-paths {
          type uint32;
          default "1";
          description
            "Maximum number of parallel paths to consider when using
             BGP multi-path. The default is use a single path.";
        }
      }
      container ibgp {
        description
          "Multi-Path parameters for iBGP";
        leaf maximum-paths {
          type uint32;
          default "1";
          description
            "Maximum number of parallel paths to consider when using
             iBGP multi-path. The default is to use a single path";
        }
      }
    }
  }

  grouping route-selection-options {
    description
      "Configuration and state relating to route selection options";
    container route-selection-options {
      description
        "Parameters relating to options for route selection";
      leaf always-compare-med {
        type boolean;
        default "false";
        description
          "Compare multi-exit discriminator (MED) value from
           different ASes when selecting the best route.  The default
           behavior is to only compare MEDs for paths received from
           the same AS.";
      }
      leaf ignore-as-path-length {
        type boolean;
        default "false";
        description
          "Ignore the AS path length when selecting the best path.
           The default is to use the AS path length and prefer paths
           with a shorter length.";
      }
      leaf external-compare-router-id {
        type boolean;
        default "true";
        description
          "When comparing similar routes received from external BGP
           peers, use the router-id as a criterion to select the
           active path.";
      }
      leaf advertise-inactive-routes {
        type boolean;
        default "false";
        description
          "Advertise inactive routes to external peers.  The default
           is to only advertise active routes.";
        reference
          "I-D.ietf-idr-best-external: Advertisement of the best
           external route in BGP.";
      }
      leaf enable-aigp {
        type boolean;
        default "false";
        description
          "Flag to enable sending / receiving accumulated IGP
           attribute in routing updates";
        reference
          "RFC 7311: AIGP Metric Attribute for BGP.";
      }
      leaf ignore-next-hop-igp-metric {
        type boolean;
        default "false";
        description
          "Ignore the IGP metric to the next-hop when calculating BGP
           best-path. The default is to select the route for which
           the metric to the next-hop is lowest";
      }
      leaf enable-med {
        type boolean;
        default "false";
        description
          "Flag to enable sending/receiving of MED metric attribute
           in routing updates.";
      }
      container med-plus-igp {
        leaf enabled {
          type boolean;
          default "false";
          description
            "When enabled allows BGP to use MED and IGP values
             defined below to determine the optimal route.";
          reference
            "RFC 4451: BGP MED Considerations.";
        }
        leaf igp-multiplier {
          type uint16;
          default 1;
          description
            "Specifies an IGP cost multiplier.";
          reference
            "RFC 4451: BGP MED Considerations.";
        }
        leaf med-multiplier {
          type uint16;
          default 1;
          description
            "Specifies a MED multiplier.";
          reference
            "RFC 4451: BGP MED Considerations.";
        }
        description
          "The med-plus-igp option enables BGP to use the sum of
           MED multiplied by a MED multiplier and IGP cost multiplied
           by IGP cost multiplier to select routes when MED is
           required to determine the optimal route.";
      }
    }
  }

  grouping state {
    description
      "Grouping containing common counters relating to prefixes and
       paths";

    container statistics {
      config false;
      description
        "Global level statistics.";

      leaf total-paths {
        type yang:gauge32;
        description
          "Total number of BGP paths (BGP routes) within the
           context";
      }

      leaf total-prefixes {
        type yang:gauge32;
        description
          "Total number of BGP prefixes (destinations) received
           within the context";
      }
    }
  }
}
